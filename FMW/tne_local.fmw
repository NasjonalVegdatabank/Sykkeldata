FME workspace tne_local.fmw

Parameters:
- DestDataset_SPATIALITE_3 = O:\Landsdekkende\Geodata\Spesialleveranser\Sykkeldatasett\Data\tne_local.db   # Destination SpatiaLite Database File

Readers:
- GEODATABASE_SDE_1: GEODATABASE_SDE

Writers:
- SPATIALITE_1: SPATIALITE to $(DestDataset_SPATIALITE_3)

Note: SDE_TNE.TNE_CurveSegment: [GEODATABASE_SDE]
SDE_TNE.TNE_CurveSegment (reader GEODATABASE_SDE_1)
    attributes: OBJECTID integer, REFLINK_OID char(38), FROM_DATE integer, TO_DATE integer, FROM_MEASURE double, TO_MEASURE double, SEG_DATE integer, LENGTH double, CLASS_CODE integer, OBJECT_CODE char(32), MEDIUM integer, QUALITY_METHOD integer, QUALITY_ACCURACY integer, QUALITY_VISIBILITY integer, QUALITY_METHOD_HEIGHT integer, QUALITY_ACCURACY_HEIGHT integer, QUALITY_TOLERANCE integer, MUNICIPALITY integer, SHAPE.LEN double
    -> curvesegment (writer SPATIALITE_1)
curvesegment (writer SPATIALITE_1)
    attributes: objectid integer, reflink_oid string(38), from_date integer, to_date integer, from_measure real(31,15), to_measure real(31,15), seg_date integer, length real(31,15), class_code integer, object_code string(32), medium integer, quality_method integer, quality_accuracy integer, quality_visibility integer, quality_method_height integer, quality_accuracy_height integer, quality_tolerance integer, municipality integer, shape_len real(31,15)
Note: SDE_TNE.TNE_FT_Vegreferanse_532_10: [GEODATABASE_SDE]
SDE_TNE.TNE_FT_Vegreferanse_532_10 (reader GEODATABASE_SDE_1)
    attributes: OBJECTID integer, NETOBJECTTV_ID char(38), FROM_DATE integer, TO_DATE integer, SEQ_NO integer, FYNR_4591 integer, KMNR_4592 integer, VKTG_4566 integer, VSOV_4570 integer, VGNR_4568 integer, HP_4569 integer, VSTS_4567 integer, FRMT_4571 integer, TLMT_4572 integer, BRK1_4576 integer, BRK2_4577 integer, VGTP_4574 integer, FVKD_4573 integer, ENRG_4707 integer, SVTP_4575 integer, MDAT_4578 date, ROUTE_ID char(38), FROM_MEASURE double, TO_MEASURE double, DIRECTION smallint, TOPOLOGY_LEVEL integer, SHAPE.LEN double
    -> vegreferanse (writer SPATIALITE_1)
vegreferanse (writer SPATIALITE_1)
    attributes: objectid integer, netobjecttv_id string(38), from_date integer, to_date integer, seq_no integer, fynr_4591 integer, kmnr_4592 integer, vktg_4566 integer, vsov_4570 integer, vgnr_4568 integer, hp_4569 integer, vsts_4567 integer, frmt_4571 integer, tlmt_4572 integer, brk1_4576 integer, brk2_4577 integer, vgtp_4574 integer, fvkd_4573 integer, enrg_4707 integer, svtp_4575 integer, mdat_4578 datetime, route_id string(38), from_measure real(31,15), to_measure real(31,15), direction integer, topology_level integer, shape_len real(31,15)
SDE_TNE.TNE_FT_Belysningsanlegg_86_10 (reader GEODATABASE_SDE_1)
    attributes: OBJECTID integer, NETOBJECTTV_ID char(38), FROM_DATE integer, TO_DATE integer, SEQ_NO integer, BA_200026_OID char(38), BA_200246_OID char(38), BA_200558_OID char(38), BA_201440_OID char(38), BROM_1271 integer, TYPE_1144 integer, NAVNS_8396 char(100), BYGGE_8399 integer, TENNS_8404 integer, MAST_3700 integer, LOST_3697 integer, STFB_3755 integer, STVE_3760 integer, EIER_5810 integer, EIERN_8397 char(100), VHAN_1554 integer, JEVNK_8743 char(100), LUMKR_8740 char(100), AVIN_1714 integer, TILSK_8398 integer, UTEDR_8400 integer, VDB_I_7656 integer, ROUTE_ID char(38), FROM_MEASURE double, TO_MEASURE double,
      SIDE smallint, TOPOLOGY_LEVEL integer, DIMMI_10001 integer, SHAPE.LEN double
    -> belysningsanlegg (writer SPATIALITE_1)
belysningsanlegg (writer SPATIALITE_1)
    attributes: objectid integer, netobjecttv_id string(38), from_date integer, to_date integer, seq_no integer, ba_200026_oid string(38), ba_200246_oid string(38), ba_200558_oid string(38), ba_201440_oid string(38), brom_1271 integer, type_1144 integer, navns_8396 string(100), bygge_8399 integer, tenns_8404 integer, mast_3700 integer, lost_3697 integer, stfb_3755 integer, stve_3760 integer, eier_5810 integer, eiern_8397 string(100), vhan_1554 integer, jevnk_8743 string(100), lumkr_8740 string(100), avin_1714 integer, tilsk_8398 integer, utedr_8400 integer, vdb_i_7656 integer, route_id string(38), from_measure real(31,15), to_measure real(31,15),
      side integer, topology_level integer, dimmi_10001 integer, shape_len real(31,15)
Note: SDE_TNE.TNE_FT_Vegfunksjon_577_10: [GEODATABASE_SDE]
SDE_TNE.TNE_FT_Vegfunksjon_577_10 (reader GEODATABASE_SDE_1)
    attributes: OBJECTID integer, NETOBJECTTV_ID char(38), FROM_DATE integer, TO_DATE integer, SEQ_NO integer, BA_200705_OID char(38), VF_5178 integer, ROUTE_ID char(38), FROM_MEASURE double, TO_MEASURE double, TOPOLOGY_LEVEL integer, SHAPE.LEN double
    -> vegfunksjon (writer SPATIALITE_1)
vegfunksjon (writer SPATIALITE_1)
    attributes: objectid integer, netobjecttv_id string(38), from_date integer, to_date integer, seq_no integer, ba_200705_oid string(38), vf_5178 integer, route_id string(38), from_measure real(31,15), to_measure real(31,15), topology_level integer, shape_len real(31,15)
Note: SDE_TNE.TNE_FT_Bruksklasse_104_10: [GEODATABASE_SDE]
SDE_TNE.TNE_FT_Bruksklasse_104_10 (reader GEODATABASE_SDE_1)
    attributes: OBJECTID integer, NETOBJECTTV_ID char(38), FROM_DATE integer, TO_DATE integer, SEQ_NO integer, BA_200239_OID char(38), BK_5179 integer, BKVIN_5180 integer, BKTEL_5181 integer, AKSTE_7576 double, MVGL_5186 integer, BRSP_5184 integer, STRBE_5183 char(500), STRSP_8800 char(500), STRTO_8801 char(500), BESKR_9308 char(250), BESKR_9309 char(250), MERK_5182 char(80), VEKTM_9125 integer, LENGM_9126 integer, VEKTT_9127 integer, LENGT_9128 integer, T100TV_9254 integer, MOBKR_9256 integer, MAXLE_8804 double, KJTLE_8805 double, MAXTO_7542 double, MAXTO_7577 double, MAXTO_7578 double, MAXTO_7579 double,
      VDB_I_7670 integer, ROUTE_ID char(38), FROM_MEASURE double, TO_MEASURE double, TOPOLOGY_LEVEL integer, STRBE_10721 char(250), MVVIN_10722 integer, MVLIN_10723 integer, SHAPE.LEN double
    -> bruksklasse (writer SPATIALITE_1)
bruksklasse (writer SPATIALITE_1)
    attributes: objectid integer, netobjecttv_id string(38), from_date integer, to_date integer, seq_no integer, ba_200239_oid string(38), bk_5179 integer, bkvin_5180 integer, bktel_5181 integer, akste_7576 real(31,15), mvgl_5186 integer, brsp_5184 integer, strbe_5183 string(500), strsp_8800 string(500), strto_8801 string(500), beskr_9308 string(250), beskr_9309 string(250), merk_5182 string(80), vektm_9125 integer, lengm_9126 integer, vektt_9127 integer, lengt_9128 integer, t100tv_9254 integer, mobkr_9256 integer, maxle_8804 real(31,15), kjtle_8805 real(31,15), maxto_7542 real(31,15), maxto_7577 real(31,15), maxto_7578 real(31,15), maxto_7579 real(31,15),
      vdb_i_7670 integer, route_id string(38), from_measure real(31,15), to_measure real(31,15), topology_level integer, strbe_10721 string(250), mvvin_10722 integer, mvlin_10723 integer, shape_len real(31,15)
Note: SDE_TNE.TNE_FT_Feltstrekning_616_10: <not set> [GEODATABASE_SDE]
SDE_TNE.TNE_FT_Feltstrekning_616_10 (reader GEODATABASE_SDE_1)
    attributes: OBJECTID integer, NETOBJECTTV_ID char(38), FROM_DATE integer, TO_DATE integer, SEQ_NO integer, FLTO_5528 char(60), ROUTE_ID char(38), FROM_MEASURE double, TO_MEASURE double, TOPOLOGY_LEVEL integer, SHAPE.LEN double
    -> feltstrekning (writer SPATIALITE_1)
feltstrekning (writer SPATIALITE_1)
    attributes: objectid integer, netobjecttv_id string(38), from_date integer, to_date integer, seq_no integer, flto_5528 string(60), route_id string(38), from_measure real(31,15), to_measure real(31,15), topology_level integer, shape_len real(31,15)
Note: SDE_TNE.TNE_FT_Fartsgrense_105_10: <not set> [GEODATABASE_SDE]
SDE_TNE.TNE_FT_Fartsgrense_105_10 (reader GEODATABASE_SDE_1)
    attributes: OBJECTID integer, NETOBJECTTV_ID char(38), FROM_DATE integer, TO_DATE integer, SEQ_NO integer, BA_200272_OID char(38), BA_200952_OID char(38), BA_201829_OID char(38), FAGR_2021 integer, VTNR_1891 char(30), VTDT_5124 date, JOURN_9155 char(40), VRFG_5125 integer, GFDT_5127 date, TIDB_2071 char(50), VDB_I_7671 integer, ROUTE_ID char(38), FROM_MEASURE double, TO_MEASURE double, LANECODE char(30), TOPOLOGY_LEVEL integer, SHAPE.LEN double
    -> fartsgrense (writer SPATIALITE_1)
fartsgrense (writer SPATIALITE_1)
    attributes: objectid integer, netobjecttv_id string(38), from_date integer, to_date integer, seq_no integer, ba_200272_oid string(38), ba_200952_oid string(38), ba_201829_oid string(38), fagr_2021 integer, vtnr_1891 string(30), vtdt_5124 datetime, journ_9155 string(40), vrfg_5125 integer, gfdt_5127 datetime, tidb_2071 string(50), vdb_i_7671 integer, route_id string(38), from_measure real(31,15), to_measure real(31,15), lanecode string(30), topology_level integer, shape_len real(31,15)
Note: SDE_TNE.TNE_FT_Gate_538_10: <not set> [GEODATABASE_SDE]
SDE_TNE.TNE_FT_Gate_538_10 (reader GEODATABASE_SDE_1)
    attributes: OBJECTID integer, NETOBJECTTV_ID char(38), FROM_DATE integer, TO_DATE integer, SEQ_NO integer, HT_200699_OID char(38), BA_201568_OID char(38), GTKD_4588 integer, GTNV_4589 char(50), ROUTE_ID char(38), FROM_MEASURE double, TO_MEASURE double, SIDE smallint, TOPOLOGY_LEVEL integer, SIDEV_9793 integer, SHAPE.LEN double
    -> gate (writer SPATIALITE_1)
gate (writer SPATIALITE_1)
    attributes: objectid integer, netobjecttv_id string(38), from_date integer, to_date integer, seq_no integer, ht_200699_oid string(38), ba_201568_oid string(38), gtkd_4588 integer, gtnv_4589 string(50), route_id string(38), from_measure real(31,15), to_measure real(31,15), side integer, topology_level integer, sidev_9793 integer, shape_len real(31,15)
Note: SDE_TNE.TNE_FT_Fortau_48_10: <not set> [GEODATABASE_SDE]
SDE_TNE.TNE_FT_Fortau_48_10 (reader GEODATABASE_SDE_1)
    attributes: OBJECTID integer, NETOBJECTTV_ID char(38), FROM_DATE integer, TO_DATE integer, SEQ_NO integer, BA_200235_OID char(38), BA_200280_OID char(38), BA_200569_OID char(38), BA_201418_OID char(38), BA_201692_OID char(38), VHAN_5638 integer, EIER_7994 integer, BEL_5637 integer, VDB_I_7633 integer, VAKA_1830 integer, ROUTE_ID char(38), FROM_MEASURE double, TO_MEASURE double, SIDE smallint, TOPOLOGY_LEVEL integer, BA_202020_OID char(38), BYGGE_10295 integer, BREDG_2241 double, BREDH_10717 integer, PUNKT_10718 integer, BA_202126_OID char(38), SHAPE.LEN double
    -> fortau (writer SPATIALITE_1)
fortau (writer SPATIALITE_1)
    attributes: objectid integer, netobjecttv_id string(38), from_date integer, to_date integer, seq_no integer, ba_200235_oid string(38), ba_200280_oid string(38), ba_200569_oid string(38), ba_201418_oid string(38), ba_201692_oid string(38), vhan_5638 integer, eier_7994 integer, bel_5637 integer, vdb_i_7633 integer, vaka_1830 integer, route_id string(38), from_measure real(31,15), to_measure real(31,15), side integer, topology_level integer, ba_202020_oid string(38), bygge_10295 integer, bredg_2241 real(31,15), bredh_10717 integer, punkt_10718 integer, ba_202126_oid string(38), shape_len real(31,15)
Note: SDE_TNE.TNE_FT_Trafikkmengde_540_10: <not set> [GEODATABASE_SDE]
SDE_TNE.TNE_FT_Trafikkmengde_540_10 (reader GEODATABASE_SDE_1)
    attributes: OBJECTID integer, NETOBJECTTV_ID char(38), FROM_DATE integer, TO_DATE integer, SEQ_NO integer, BA_200670_OID char(38), BA_201812_OID char(38), TADT_4623 integer, LANGX_4624 integer, AR_4621 integer, OPFR_6843 integer, GRLG_4625 integer, ANID_4620 char(4), TRAFA_7477 integer, TPPM_5219 integer, TPSD_5222 integer, FADT_5220 double, FLNG_5221 double, KPAR_5223 integer, MFAK_4622 double, AADTS_7475 integer, AADTS_7476 integer, VDB_I_7804 integer, ROUTE_ID char(38), FROM_MEASURE double, TO_MEASURE double, TOPOLOGY_LEVEL integer, SHAPE.LEN double
    -> trafikkmengde (writer SPATIALITE_1)
trafikkmengde (writer SPATIALITE_1)
    attributes: objectid integer, netobjecttv_id string(38), from_date integer, to_date integer, seq_no integer, ba_200670_oid string(38), ba_201812_oid string(38), tadt_4623 integer, langx_4624 integer, ar_4621 integer, opfr_6843 integer, grlg_4625 integer, anid_4620 string(4), trafa_7477 integer, tppm_5219 integer, tpsd_5222 integer, fadt_5220 real(31,15), flng_5221 real(31,15), kpar_5223 integer, mfak_4622 real(31,15), aadts_7475 integer, aadts_7476 integer, vdb_i_7804 integer, route_id string(38), from_measure real(31,15), to_measure real(31,15), topology_level integer, shape_len real(31,15)
Note: SDE_TNE.TNE_FT_ikfb_606_10: <not set> [GEODATABASE_SDE]
SDE_TNE.TNE_FT_ikfb_606_10 (reader GEODATABASE_SDE_1)
    attributes: OBJECTID integer, NETOBJECTTV_ID char(38), FROM_DATE integer, TO_DATE integer, SEQ_NO integer, BA_200801_OID char(38), MRK_5476 char(200), SKNR_5475 char(7), ROUTE_ID char(38), FROM_MEASURE double, TO_MEASURE double, SIDE smallint, DIRECTION smallint, LANECODE char(30), TOPOLOGY_LEVEL integer, SHAPE.LEN double
    -> ikfb (writer SPATIALITE_1)
ikfb (writer SPATIALITE_1)
    attributes: objectid integer, netobjecttv_id string(38), from_date integer, to_date integer, seq_no integer, ba_200801_oid string(38), mrk_5476 string(200), sknr_5475 string(7), route_id string(38), from_measure real(31,15), to_measure real(31,15), side integer, direction integer, lanecode string(30), topology_level integer, shape_len real(31,15)
Note: SDE_TNE.TNE_FT_Tunnellop_67_10: <not set> [GEODATABASE_SDE]
SDE_TNE.TNE_FT_Tunnellop_67_10 (reader GEODATABASE_SDE_1)
    attributes: OBJECTID integer, NETOBJECTTV_ID char(38), FROM_DATE integer, TO_DATE integer, SEQ_NO integer, KATEG_8944 integer, TUNLP_1977 integer, TYPE_1130 integer, LENG_1317 double, AREA_1367 double, BRED_3897 double, APNIN_8356 integer, USJO_5272 integer, SKFB_3899 integer, INNBE_7864 integer, BRUTU_9305 char(30), INNR_2178 char(10), MERK_5286 char(50), VDB_I_7642 integer, BA_200031_OID char(38), BA_200061_OID char(38), BA_200167_OID char(38), BA_200187_OID char(38), BA_200201_OID char(38), BA_200202_OID char(38), BA_200203_OID char(38), BA_200205_OID char(38), BA_200407_OID char(38), BA_200464_OID char(38), BA_200739_OID char(38),
      BA_200740_OID char(38), BA_200741_OID char(38), BA_200742_OID char(38), BA_200743_OID char(38), BA_200744_OID char(38), BA_200745_OID char(38), BA_200746_OID char(38), BA_200747_OID char(38), BA_200749_OID char(38), BA_200751_OID char(38), BA_200755_OID char(38), BA_200757_OID char(38), BA_200759_OID char(38), BA_200760_OID char(38), BA_200761_OID char(38), BA_200762_OID char(38), BA_200763_OID char(38), BA_200764_OID char(38), BA_200765_OID char(38), BA_200766_OID char(38), BA_200767_OID char(38), BA_200768_OID char(38), BA_200769_OID char(38), BA_200770_OID char(38), BA_200772_OID char(38), BA_200774_OID char(38), BA_200775_OID char(38), BA_200776_OID char(38), BA_200777_OID char(38), BA_200779_OID char(38),
      BA_200781_OID char(38), BA_200782_OID char(38), BA_200784_OID char(38), BA_200786_OID char(38), BA_200811_OID char(38), BA_200812_OID char(38), BA_200813_OID char(38), BA_200815_OID char(38), BA_200816_OID char(38), BA_200817_OID char(38), BA_200818_OID char(38), BA_200819_OID char(38), BA_200839_OID char(38), BA_201427_OID char(38), BA_201637_OID char(38), BA_201815_OID char(38), BA_201819_OID char(38), BA_201830_OID char(38), BA_201833_OID char(38), BA_201868_OID char(38), BA_201869_OID char(38), BA_201874_OID char(38), BA_201877_OID char(38), BA_201878_OID char(38), NAVN_1081 char(50), ROUTE_ID char(38), FROM_MEASURE double, TO_MEASURE double, SIDE smallint, LANECODE char(30),
      TOPOLOGY_LEVEL integer, BA_201885_OID char(38), BA_201893_OID char(38), BA_201894_OID char(38), BA_200081_OID char(38), BA_201971_OID char(38), BA_202006_OID char(38), BA_202035_OID char(38), BA_202041_OID char(38), BA_202042_OID char(38), BA_202046_OID char(38), BA_202038_OID char(38), BA_202039_OID char(38), BA_202083_OID char(38), BA_202103_OID char(38), REHAB_10693 integer, SHAPE.LEN double
    -> tunnellop (writer SPATIALITE_1)
tunnellop (writer SPATIALITE_1)
    attributes: objectid integer, netobjecttv_id string(38), from_date integer, to_date integer, seq_no integer, kateg_8944 integer, tunlp_1977 integer, type_1130 integer, leng_1317 real(31,15), area_1367 real(31,15), bred_3897 real(31,15), apnin_8356 integer, usjo_5272 integer, skfb_3899 integer, innbe_7864 integer, brutu_9305 string(30), innr_2178 string(10), merk_5286 string(50), vdb_i_7642 integer, ba_200031_oid string(38), ba_200061_oid string(38), ba_200167_oid string(38), ba_200187_oid string(38), ba_200201_oid string(38), ba_200202_oid string(38), ba_200203_oid string(38), ba_200205_oid string(38), ba_200407_oid string(38), ba_200464_oid string(38), ba_200739_oid string(38),
      ba_200740_oid string(38), ba_200741_oid string(38), ba_200742_oid string(38), ba_200743_oid string(38), ba_200744_oid string(38), ba_200745_oid string(38), ba_200746_oid string(38), ba_200747_oid string(38), ba_200749_oid string(38), ba_200751_oid string(38), ba_200755_oid string(38), ba_200757_oid string(38), ba_200759_oid string(38), ba_200760_oid string(38), ba_200761_oid string(38), ba_200762_oid string(38), ba_200763_oid string(38), ba_200764_oid string(38), ba_200765_oid string(38), ba_200766_oid string(38), ba_200767_oid string(38), ba_200768_oid string(38), ba_200769_oid string(38), ba_200770_oid string(38), ba_200772_oid string(38), ba_200774_oid string(38), ba_200775_oid string(38), ba_200776_oid string(38), ba_200777_oid string(38), ba_200779_oid string(38),
      ba_200781_oid string(38), ba_200782_oid string(38), ba_200784_oid string(38), ba_200786_oid string(38), ba_200811_oid string(38), ba_200812_oid string(38), ba_200813_oid string(38), ba_200815_oid string(38), ba_200816_oid string(38), ba_200817_oid string(38), ba_200818_oid string(38), ba_200819_oid string(38), ba_200839_oid string(38), ba_201427_oid string(38), ba_201637_oid string(38), ba_201815_oid string(38), ba_201819_oid string(38), ba_201830_oid string(38), ba_201833_oid string(38), ba_201868_oid string(38), ba_201869_oid string(38), ba_201874_oid string(38), ba_201877_oid string(38), ba_201878_oid string(38), navn_1081 string(50), route_id string(38), from_measure real(31,15), to_measure real(31,15), side integer, lanecode string(30),
      topology_level integer, ba_201885_oid string(38), ba_201893_oid string(38), ba_201894_oid string(38), ba_200081_oid string(38), ba_201971_oid string(38), ba_202006_oid string(38), ba_202035_oid string(38), ba_202041_oid string(38), ba_202042_oid string(38), ba_202046_oid string(38), ba_202038_oid string(38), ba_202039_oid string(38), ba_202083_oid string(38), ba_202103_oid string(38), rehab_10693 integer, shape_len real(31,15)
Note: SDE_TNE.TNE_FT_Tunnel_581_10: <not set> [GEODATABASE_SDE]
SDE_TNE.TNE_FT_Tunnel_581_10 (reader GEODATABASE_SDE_1)
    attributes: OBJECTID integer, NETOBJECTTV_ID char(38), FROM_DATE integer, TO_DATE integer, SEQ_NO integer, BA_200710_OID char(38), BA_200711_OID char(38), BA_200714_OID char(38), BA_200752_OID char(38), BA_200778_OID char(38), BA_200785_OID char(38), NAVN_5225 char(50), TUNNE_9306 char(10), TUNNE_9134 integer, PARHL_3947 integer, LENSK_8945 integer, LENLO_8150 integer, LENRA_8151 integer, UNDER_9517 integer, SYKKE_9518 integer, TLFVT_3917 integer, ALBRA_3918 integer, KBSN_3915 integer, KBNG_3916 integer, BRANN_9507 date, RESTR_9131 integer, MRKRE_9506 char(1073741822), MKSY_3913 char(50), BRUTU_9329 char(30), ROUTE_ID char(38),
      MEASURE double, TOPOLOGY_LEVEL integer, XLHT_3947 integer, BPGK_3919 integer, BPLAN_9132 integer, UPBA_3914 integer, SNGT_3917 integer, AVFB_3918 integer, APNEA_10383 integer, BA_202110_OID char(38)
    -> tunnel (writer SPATIALITE_1)
tunnel (writer SPATIALITE_1)
    attributes: objectid integer, netobjecttv_id string(38), from_date integer, to_date integer, seq_no integer, ba_200710_oid string(38), ba_200711_oid string(38), ba_200714_oid string(38), ba_200752_oid string(38), ba_200778_oid string(38), ba_200785_oid string(38), navn_5225 string(50), tunne_9306 string(10), tunne_9134 integer, parhl_3947 integer, lensk_8945 integer, lenlo_8150 integer, lenra_8151 integer, under_9517 integer, sykke_9518 integer, tlfvt_3917 integer, albra_3918 integer, kbsn_3915 integer, kbng_3916 integer, brann_9507 datetime, restr_9131 integer, mrkre_9506 string(1073741822), mksy_3913 string(50), brutu_9329 string(30), route_id string(38),
      measure real(31,15), topology_level integer, xlht_3947 integer, bpgk_3919 integer, bplan_9132 integer, upba_3914 integer, sngt_3917 integer, avfb_3918 integer, apnea_10383 integer, ba_202110_oid string(38)
Note: SDE_TNE.TNE_FT_Motorveg_595_10: <not set> [GEODATABASE_SDE]
SDE_TNE.TNE_FT_Motorveg_595_10 (reader GEODATABASE_SDE_1)
    attributes: OBJECTID integer, NETOBJECTTV_ID char(38), FROM_DATE integer, TO_DATE integer, SEQ_NO integer, BA_200790_OID char(38), MVEGT_5378 integer, VTAKD_5377 date, VEDTA_5376 char(10), ROUTE_ID char(38), FROM_MEASURE double, TO_MEASURE double, TOPOLOGY_LEVEL integer, JOURN_9485 char(40), BYGGE_10328 integer, SHAPE.LEN double
    -> motorveg (writer SPATIALITE_1)
motorveg (writer SPATIALITE_1)
    attributes: objectid integer, netobjecttv_id string(38), from_date integer, to_date integer, seq_no integer, ba_200790_oid string(38), mvegt_5378 integer, vtakd_5377 datetime, vedta_5376 string(10), route_id string(38), from_measure real(31,15), to_measure real(31,15), topology_level integer, journ_9485 string(40), bygge_10328 integer, shape_len real(31,15)
