FME workspace sammenstilling.fmw

Parameters:
- Kommunevise_db = C:\DATA\Sykkelreiseplanlegger\Data\Kommunevise\Sykkeldata_*.db   # Kommunevise SpatiaLite-baser
- Sykkelruter:SHP = C:\DATA\Sykkelreiseplanlegger\Data\Nasjonale ruter\bicycle_routes_lin.shp   # Sykkelruter (SHAPE)
- Ut_Mappe = C:\DATA\Sykkelreiseplanlegger\Data   # Mappe for utdata
- Datert_db:   # Python Script
      import fmeobjects
      import datetime
      
      par = ''
      now = datetime.datetime.now()
      cYear=now.year
      cMonth=now.month
      cDay=now.day
      par = FME_MacroValues['Ut_Mappe']+'\Sykkeldata_'+str(cYear)+str(cMonth).zfill(2)+str(cDay).zfill(2)+'.db'
      return par
- Datert_FGDB:   # Python Script
      import fmeobjects
      import datetime
      
      par = ''
      now = datetime.datetime.now()
      cYear=now.year
      cMonth=now.month
      cDay=now.day
      par = FME_MacroValues['Ut_Mappe']+'\Sykkeldata_'+str(cYear)+str(cMonth).zfill(2)+str(cDay).zfill(2)+'.gdb'
      return par

Readers:
- SPATIALITE_1: SPATIALITE from $(Kommunevise_db)
- SHAPE_1: SHAPE from $(Sykkelruter:SHP)

Writers:
- SPATIALITE_2: SPATIALITE to $(Datert_db)
- GEODATABASE_FILE_1: GEODATABASE_FILE to $(Datert_FGDB)

noder (reader SPATIALITE_1)
    attributes: nodeid string(255)
    -> CoordinateRounder
CoordinateRounder
    YPREC = 2
    XPREC = 2
    ZPREC = 2
    ROUNDED -> Matcher
Matcher
    MATCH_STRATEGY = Match Selected Attributes
    LENIENT_MATCH = No
    BLANK_AND_MISSING_DIFFER = No
    MATCH = 2D
    CNT_ATTR = _match_id
    SINGLE_MATCHED -> TopologyBuilder
    NOT_MATCHED -> TopologyBuilder
lenker (reader SPATIALITE_1)
    attributes: andel_lange string(255), kilde string(255), belysning string(255), vegnavn string(255), aadt string(255), medium string(255), trafikkretning string(255), fartsgrense string(255), startnode string(255), sykkelforbud string(255), typeveg string(255), sluttnode string(255)
    -> CoordinateRounder_2
CoordinateRounder_2
    YPREC = 2
    XPREC = 2
    ZPREC = 2
    ROUNDED -> Matcher_2
Matcher_2
    MATCH_STRATEGY = Match Selected Attributes
    MATCHATTRS = kilde medium typeveg sykkelforbud belysning vegnavn trafikkretning aadt fartsgrense andel_lange
    LENIENT_MATCH = No
    BLANK_AND_MISSING_DIFFER = No
    MATCH = 2D
    CNT_ATTR = _match_id
    SINGLE_MATCHED -> TopologyBuilder
    NOT_MATCHED -> TopologyBuilder
TopologyBuilder
    ALLOW_CYCLES = No
    CLEAN_DATA = Yes
    MAX = 0
    PROP_ATTRS = No
    DEAGGREGATE_INPUT = Yes
    BOUNDING_EDGES = All
    OVERLAPPING_MODE = No
    NODE -> AttributeRenamer
    LINE -> AttributeRenamer_2
AttributeRenamer
    ATTR_TABLE = RENAME_SET_DEFAULT _node_number > nodeid
    -> noder (writer SPATIALITE_2)
    -> noder (writer GEODATABASE_FILE_1)
noder (writer GEODATABASE_FILE_1)
    attributes: nodeid char(255)
noder (writer SPATIALITE_2)
    attributes: nodeid string(255)
AttributeRenamer_2
    ATTR_TABLE:
      RENAME_SET_DEFAULT _from_node > startnode
      RENAME_SET_DEFAULT _to_node > sluttnode
    -> lenker (writer SPATIALITE_2)
    -> lenker (writer GEODATABASE_FILE_1)
lenker (writer GEODATABASE_FILE_1)
    attributes: andel_lange char(255), kilde char(255), belysning char(255), vegnavn char(255), aadt char(255), medium char(255), trafikkretning char(255), fartsgrense char(255), startnode char(255), sykkelforbud char(255), typeveg char(255), sluttnode char(255)
lenker (writer SPATIALITE_2)
    attributes: andel_lange string(255), kilde string(255), belysning string(255), vegnavn string(255), aadt string(255), medium string(255), trafikkretning string(255), fartsgrense string(255), startnode string(255), sykkelforbud string(255), typeveg string(255), sluttnode string(255)
bicycle_routes_lin (reader SHAPE_1)
    attributes: GID number(11,0), OBJECTID number(11,0), COMMENTS char(25), NAME char(50), TYPE char(50), SHAPE_LENG number(19,15)
    -> Generalizer
Generalizer
    ALG_TEXT = NURBfit (Smooth)
    PRESERVE = No
    DEGREE = 50
    SEGMENT_LENGTH = 50
    -> AttributeManager
AttributeManager
    ATTR_TABLE:
      RENAME_SET_VALUE TYPE > type
      RENAME_SET_VALUE NAME > name
    NUM_PRIOR_FEATURES = 0
    NUM_SUBSEQUENT_FEATURES = 0
    -> sykkelruter (writer SPATIALITE_2)
    -> sykkelruter (writer GEODATABASE_FILE_1)
sykkelruter (writer GEODATABASE_FILE_1)
    attributes: name char(255), type char(255)
sykkelruter (writer SPATIALITE_2)
    attributes: name string(50), type string(50)
frinavigeringssoner (reader SPATIALITE_1)
    attributes: navn string(255), type string(255)
    -> frinavigeringssoner (writer SPATIALITE_2)
    -> frinavigeringssoner (writer GEODATABASE_FILE_1)
frinavigeringssoner (writer GEODATABASE_FILE_1)
    attributes: navn char(255), type char(255)
frinavigeringssoner (writer SPATIALITE_2)
    attributes: navn string(255), type string(255)
