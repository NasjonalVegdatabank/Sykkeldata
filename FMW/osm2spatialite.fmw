FME workspace osm2spatialite.fmw
Startup Python:
      import urllib2, fme, os

      proxy = urllib2.ProxyHandler({'http': 'proxy.vegvesen.no:8080'})
      opener = urllib2.build_opener(proxy)
      urllib2.install_opener(opener)

      osmDir = FME_MacroValues['osmDir']
      osmFile = FME_MacroValues['osmFile']
      filename = osmDir + '\\' + osmFile
      pbf = filename + '.pbf'
      o5m = filename + '.o5m'
      url = FME_MacroValues['osmURL']
      download = FME_MacroValues['download']

      if download == 'Yes':
          print 'Downloading file ' + url + ' to ' + pbf
          with open(pbf,'wb') as f:
              f.write(urllib2.urlopen(url).read())
              f.close()
          print 'Download complete'

      print 'Converting file ' + pbf + ' to o5m format'
      cmd = osmDir + '\\osmconvert ' + pbf + ' -o=' + o5m
      os.system(cmd)

      print 'Filtering file ' + o5m
      cmd=osmDir + '\\osmfilter ' + o5m + ' --parameter-file=' + osmDir + '\\osm_select.par >' + osmDir + '\\' + 'filtered-' + osmFile
      os.system(cmd)

Parameters:
- download = Yes   # Download file
- mDir = O:\Landsdekkende\Geodata\Spesialleveranser\Sykkeldatasett\Data   # Main directory
- osmURL = http://download.geofabrik.de/europe/norway-latest.osm.pbf   # *.pbf URL to OpenStreetMap file (Geofabrik)
- osmFile = norway-latest.osm   # Local OSM file
- osmDir = FME_MacroValues['mDir'] + '\\OSM'   # Python Script
- osmFiltered = FME_MacroValues['mDir'] + '\\OSM\\filtered-' + FME_MacroValues['osmFile']   # Python Script
- osmOut = FME_MacroValues['mDir'] + '\\OSM\\Norge_UTM33.db'   # Python Script

Readers:
- OSM_1: OSM from $(osmFiltered)

Writers:
- SPATIALITE_1: SPATIALITE to $(osmOut) in EPSG:25833

shop (reader OSM_1)
    attributes: created_by xml_buffer, area xml_buffer, layer xml_buffer, tag{}.k xml_buffer, tag{}.v xml_buffer, nd{}.ref xml_buffer, member{}.type xml_buffer, member{}.ref xml_buffer, member{}.role xml_buffer, shop xml_buffer
    -> AttributeExposer
route (reader OSM_1)
    attributes: created_by xml_buffer, area xml_buffer, layer xml_buffer, tag{}.k xml_buffer, tag{}.v xml_buffer, nd{}.ref xml_buffer, member{}.type xml_buffer, member{}.ref xml_buffer, member{}.role xml_buffer, route xml_buffer
    -> AttributeExposer
highway (reader OSM_1)
    attributes: created_by xml_buffer, area xml_buffer, layer xml_buffer, tag{}.k xml_buffer, tag{}.v xml_buffer, nd{}.ref xml_buffer, member{}.type xml_buffer, member{}.ref xml_buffer, member{}.role xml_buffer, highway xml_buffer
    -> AttributeExposer
buidling (reader OSM_1)
    attributes: created_by xml_buffer, area xml_buffer, layer xml_buffer, tag{}.k xml_buffer, tag{}.v xml_buffer, nd{}.ref xml_buffer, member{}.type xml_buffer, member{}.ref xml_buffer, member{}.role xml_buffer, buidling xml_buffer
    -> AttributeExposer
building (reader OSM_1)
    attributes: created_by xml_buffer, area xml_buffer, layer xml_buffer, tag{}.k xml_buffer, tag{}.v xml_buffer, nd{}.ref xml_buffer, member{}.type xml_buffer, member{}.ref xml_buffer, member{}.role xml_buffer, building xml_buffer
    -> AttributeExposer
amenity (reader OSM_1)
    attributes: created_by xml_buffer, area xml_buffer, layer xml_buffer, tag{}.k xml_buffer, tag{}.v xml_buffer, nd{}.ref xml_buffer, member{}.type xml_buffer, member{}.ref xml_buffer, member{}.role xml_buffer, amenity xml_buffer
    -> AttributeExposer
AttributeExposer
    ATTR_LIST = tag.area,parking,highway,bicycle,footway,service,route,motor_vehicle,oneway,bicycle:backward,bicycle:oneway,oneway:bicycle,cycleway,cycleway:left,cycleway:right,name
    -> FeatureTypeFilter
FeatureTypeFilter
    ATTRIBUTES = <BLANK>,<UNFILTERED>,amenity,building,shop,highway,route
    amenity -> GeometryFilter
    building -> FeatureTypeFilter_shop_-__GeometryFilter_2
    shop -> FeatureTypeFilter_shop_-__GeometryFilter_2
    highway -> GeometryFilter_3
    route -> TestFilter_2
TestFilter_2_Resten_-__TestFilter_3: Junction
    -> TestFilter_3
    -> TestFilter_2_Resten_-__TestFilter_5
Note: Finner aktuelle lenker
TestFilter_3
    TEST_LIST:
      BOOL_OP,AND,COMPOSITE_TEST,<Unused>,TEST_CLAUSE,"TEST @Value(highway) = footway
      TEST @Value(footway) = crossing",Gangfelt,BOOL_OP,AND,COMPOSITE_TEST,<Unused>,TEST_CLAUSE,"TEST @Value(highway) = footway
      TEST @Value(footway) = sidewalk",Fortau,BOOL_OP,COMPOSITE,COMPOSITE_TEST,"""(1 AND 2 AND 3) OR 4""",TEST_CLAUSE,"TEST @Value(highway) = footway
      TEST @Value(footway) != crossing
      TEST @Value(bicycle) != no
      TEST @Value(highway) = pedestrian",Gangveg,BOOL_OP,AND,COMPOSITE_TEST,<Unused>,TEST_CLAUSE,"TEST @Value(highway) = cycleway",Gang- og sykkelveg ,BOOL_OP,AND,COMPOSITE_TEST,<Unused>,TEST_CLAUSE,"TEST @Value(highway) = service
      TEST @Value(service) = parking_aisle",Parkeringsfil,BOOL_OP,AND,COMPOSITE_TEST,<Unused>,TEST_CLAUSE,"TEST @Value(highway) = service
      TEST @Value(service) = driveway",Innkjørsel,BOOL_OP,AND,COMPOSITE_TEST,<Unused>,TEST_CLAUSE,"TEST @Value(highway) = service
      TEST service ATTRIBUTE_IS_MISSING """"",Stikkveg,BOOL_OP,AND,COMPOSITE_TEST,<Unused>,TEST_CLAUSE,"TEST @Value(highway) = track",StorSti,BOOL_OP,AND,COMPOSITE_TEST,<Unused>,TEST_CLAUSE,"TEST @Value(highway) = path",Sti,BOOL_OP,AND,COMPOSITE_TEST,<Unused>,TEST_CLAUSE,"TEST @Value(highway) = steps",Trapp,BOOL_OP,AND,COMPOSITE_TEST,<Unused>,TEST_CLAUSE,"TEST @Value(route) = ferry
      TEST @Value(motor_vehicle) = no",Passasjerferje
    DEFAULT_VALUE = <UNFILTERED>
    Gangfelt -> AttributeCreator_5
    Fortau -> AttributeCreator_9
    Gangveg -> AttributeCreator_7
    Gang- og sykkelveg -> AttributeCreator_8
    Parkeringsfil -> AttributeCreator_10
    Innkjørsel -> AttributeCreator_11
    Stikkveg -> AttributeCreator_33
    StorSti -> AttributeCreator_24
    Sti -> AttributeCreator_25
    Trapp -> AttributeCreator_26
    Passasjerferje -> AttributeCreator_32
Note: trafikkretning og sykkelforbud
AttributeCreator_12
    ATTR_LIST = trafikkretning,"FME_CONDITIONAL:DEFAULT_VALUE'BEGGE'BOOL_OP;COMPOSITE;COMPOSITE_TEST;(1 OR 2 OR 3) AND 4 AND 5 AND 6 AND 7 AND 8 AND 9 AND 10 AND 11;TEST @Value(oneway) = yes;TEST @Value(oneway) = true;TEST @Value(oneway) = 1;TEST @Value(bicycle:backward) != yes;TEST @Value(bicycle:oneway) != no;TEST @Value(oneway:bicycle) != no;TEST @Value(cycleway) != opposite;TEST @Value(cycleway) != opposite_lane;TEST @Value(cycleway:left) != lane;TEST @Value(cycleway:left) != opposite;TEST @Value(cycleway:left) != opposite_lane'MED'BOOL_OP;COMPOSITE;COMPOSITE_TEST;(1 OR 2) AND 3 AND 4 AND 5;TEST @Value(oneway) = -1;TEST @Value(oneway) = reverse;TEST @Value(cycleway:right) != lane;TEST @Value(cycleway:right) != opposite;TEST @Value(cycleway:right) != opposite_lane'MOT'FME_NUM_CONDITIONS3___",sykkelforbud,"FME_CONDITIONAL:DEFAULT_VALUE'Nei'BOOL_OP;OR;COMPOSITE_TEST;<Unused>;TEST @Value(bicycle) = no'Ja'FME_NUM_CONDITIONS2___"
    -> AttributeCreator_15
TestFilter_2_Resten_-__TestFilter_5: Junction
    -> TestFilter_5
    -> TestFilter_6
Note: vegnavn og medium
AttributeCreator_15
    ATTR_LIST = vegnavn,"FME_CONDITIONAL:DEFAULT_VALUE'@Value(name)'BOOL_OP;OR;COMPOSITE_TEST;<Unused>;TEST name ATTRIBUTE_IS_MISSING _FME_BLANK_STRING_'@Value(typeveg)'FME_NUM_CONDITIONS2___",medium,"FME_CONDITIONAL:DEFAULT_VALUE'T'BOOL_OP;OR;COMPOSITE_TEST;<Unused>;TEST bridge NOT_ATTRIBUTE_IS_MISSING _FME_BLANK_STRING_'L'BOOL_OP;OR;COMPOSITE_TEST;<Unused>;TEST tunnel NOT_ATTRIBUTE_IS_MISSING _FME_BLANK_STRING_'U'FME_NUM_CONDITIONS3___"
    -> GeometryValidator
GeometryValidator
    NULL_REMOVAL = NULL_REMOVAL
    ISSUE_ATTR_NAME = _issues
    REPAIR = Yes
    ARC_ENDPOINT_TOLERANCE_MODE = Auto
    PRESETS = Basic Geometry Integrity
    NAN_REMOVAL = NAN_REMOVAL
    SUMMARY = Detailed
    CONNECT_Z_MODE_TR = First Wins
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    TYPE_REPAIR = TYPE_REPAIR
    PASSED -> lenker (writer SPATIALITE_1)
    REPAIRED -> lenker (writer SPATIALITE_1)
Note: lenker
lenker (writer SPATIALITE_1)
    attributes: typeveg string(2), vegnavn string(50), medium string(2), trafikkretning string(10), andel_lange string(255), kilde string(255), belysning string(255), aadt string(255), startnode string(255), fartsgrense string(255), sykkelforbud string(255), sluttnode string(255)
FeatureTypeFilter_shop_-__GeometryFilter_2: Junction
    -> GeometryFilter_2

Bookmark: Frinavigeringssoner
GeometryFilter
    INSTANTIATE = No
    BREAK_AGG = No
    GEOM_PORT_NAMES = Area
    AREA -> TestFilter
TestFilter
    TEST_LIST:
      BOOL_OP,COMPOSITE,COMPOSITE_TEST,"""1 AND (2 OR 3)""",TEST_CLAUSE,"TEST @Value(amenity) = parking
      TEST @Value(parking) = surface
      TEST parking ATTRIBUTE_IS_MISSING """"",Parkeringsplass,BOOL_OP,OR,COMPOSITE_TEST,<Unused>,TEST_CLAUSE,"TEST @Value(amenity) = marketplace",Torg
    DEFAULT_VALUE = <UNFILTERED>
    Parkeringsplass -> AttributeCreator_2
    Torg -> AttributeCreator_3
Note: type=Parkeringsplass
AttributeCreator_2
    ATTR_LIST = type,Parkeringsplass
    -> AttributeCreator_2_OUTPUT_-__AttributeCreator
Note: type=Torg
AttributeCreator_3
    ATTR_LIST = type,Torg/plass
    -> AttributeCreator_2_OUTPUT_-__AttributeCreator
AttributeCreator_2_OUTPUT_-__AttributeCreator: Junction
    -> AttributeCreator
GeometryFilter_3
    BREAK_AGG = No
    GEOM_PORT_NAMES = Area Line
    AREA -> AttributeCreator_4
    LINE -> TestFilter_2
TestFilter_2
    TEST_LIST:
      BOOL_OP,OR,COMPOSITE_TEST,<Unused>,TEST_CLAUSE,"TEST @Value(area) = yes
      TEST @Value(tag.area) = yes",Area_yes
    DEFAULT_VALUE = Resten
    Area_yes -> TestFilter_4
    Resten -> TestFilter_2_Resten_-__TestFilter_3
Note: Fotgjengerområder som ligger som linje, men med area=yes
TestFilter_4
    TEST_LIST = BOOL_OP,AND,COMPOSITE_TEST,<Unused>,TEST_CLAUSE,"TEST @Value(highway) = pedestrian",Fotgjengerområde
    DEFAULT_VALUE = <UNFILTERED>
    Fotgjengerområde -> AreaBuilder
AreaBuilder
    DONUT_CREATION = Yes
    SNAP_TOLERANCE = 0
    SNAPTYPE_PARAM = None
    ALLOW_CYCLES = No
    DROP_HOLES = No
    LINES_AS_SEGMENTS = No
    AREA -> AttributeCreator_4
Note: type=Fotgjengerområde
AttributeCreator_4
    ATTR_LIST = type,Fotgjengerområde
    -> AttributeCreator
Note: navn
AttributeCreator
    ATTR_LIST = navn,"FME_CONDITIONAL:DEFAULT_VALUE'@Value(name)'BOOL_OP;OR;COMPOSITE_TEST;<Unused>;TEST name ATTRIBUTE_IS_MISSING _FME_BLANK_STRING_'@Value(type)'FME_NUM_CONDITIONS2___"
    -> GeometryValidator_2
GeometryValidator_2
    NULL_REMOVAL = NULL_REMOVAL
    ISSUE_ATTR_NAME = _issues
    REPAIR = Yes
    ARC_ENDPOINT_TOLERANCE_MODE = Auto
    PRESETS = Basic Geometry Integrity
    NAN_REMOVAL = NAN_REMOVAL
    SUMMARY = Detailed
    CONNECT_Z_MODE_TR = First Wins
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    TYPE_REPAIR = TYPE_REPAIR
    PASSED -> frinavigeringssoner (writer SPATIALITE_1)
    REPAIRED -> frinavigeringssoner (writer SPATIALITE_1)
frinavigeringssoner (writer SPATIALITE_1)
    attributes: navn string(30), type string(30)
GeometryFilter_2
    INSTANTIATE = No
    BREAK_AGG = No
    GEOM_PORT_NAMES = Area
    AREA -> GeometryValidator_3
GeometryValidator_3
    NULL_REMOVAL = NULL_REMOVAL
    ISSUE_ATTR_NAME = _issues
    REPAIR = Yes
    ARC_ENDPOINT_TOLERANCE_MODE = Auto
    PRESETS = Basic Geometry Integrity
    NAN_REMOVAL = NAN_REMOVAL
    SUMMARY = Detailed
    CONNECT_Z_MODE_TR = First Wins
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    TYPE_REPAIR = TYPE_REPAIR
    PASSED -> bygninger (writer SPATIALITE_1)
    REPAIRED -> bygninger (writer SPATIALITE_1)
bygninger (writer SPATIALITE_1)
    attributes: building string(255), shop string(255)

Bookmark: typeveg
AttributeCreator_5
    ATTR_LIST = typeveg,Gangfelt
    -> AttributeCreator_12
AttributeCreator_9
    ATTR_LIST = typeveg,Fortau
    -> AttributeCreator_12
AttributeCreator_7
    ATTR_LIST = typeveg,Gangveg
    -> AttributeCreator_12
AttributeCreator_8
    ATTR_LIST = typeveg,Gang- og sykkelveg
    -> AttributeCreator_12
AttributeCreator_10 [off]
    ATTR_LIST = typeveg,Parkeringsfil
    -> AttributeCreator_12 [off]
AttributeCreator_11
    ATTR_LIST = typeveg,Privat veg
    -> AttributeCreator_12
AttributeCreator_33 [off]
    ATTR_LIST = typeveg,Stikkveg
    -> AttributeCreator_12 [off]
AttributeCreator_24
    ATTR_LIST = typeveg,Stor sti
    -> AttributeCreator_12
AttributeCreator_25 [off]
    ATTR_LIST = typeveg,Sti
    -> AttributeCreator_12 [off]
AttributeCreator_26
    ATTR_LIST = typeveg,Trapp
    -> AttributeCreator_12
AttributeCreator_32
    ATTR_LIST = typeveg,Passasjerferje
    -> AttributeCreator_12

Bookmark: En lenke pr sykkelfelt
Note: Sykkelfelt med geometriretning
TestFilter_5
    TEST_LIST:
      BOOL_OP,OR,COMPOSITE_TEST,<Unused>,TEST_CLAUSE,"TEST @Value(cycleway) IN lane,lane;opposite_lane
      TEST @Value(cycleway:right) = lane",Sykkelfelt med
    DEFAULT_VALUE = <UNFILTERED>
    Sykkelfelt med -> AttributeCreator_13
Note: trafikkretning MED
AttributeCreator_13
    ATTR_LIST = trafikkretning,MED
    -> AttributeCreator_6
Note: Sykkelfelt mot geometriretning
TestFilter_6
    TEST_LIST:
      BOOL_OP,COMPOSITE,COMPOSITE_TEST,"""1 OR 2 OR (3 AND 4)""",TEST_CLAUSE,"TEST @Value(cycleway) IN opposite_lane,lane;opposite_lane
      TEST @Value(cycleway:left) IN lane, opposite_lane
      TEST @Value(cycleway) = lane
      TEST @Value(oneway) NOT_IN yes,1,true",Sykkelfelt mot
    DEFAULT_VALUE = <UNFILTERED>
    Sykkelfelt mot -> AttributeCreator_14
Note: trafikkretning MOT
AttributeCreator_14
    ATTR_LIST = trafikkretning,MOT
    -> AttributeCreator_6
Note: typeveg=Sykkelfelt, sykkelforbud=nei
AttributeCreator_6
    ATTR_LIST = typeveg,Sykkelfelt,sykkelforbud,Nei
    -> AttributeCreator_15
