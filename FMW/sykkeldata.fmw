FME workspace sykkeldata.fmw
History: 20150916,knjetl,Snapping til frinavigeringssoner, og buffer på frinavigeringsonene,20150916,knjetl,Snapping (15cm) for alle lenker, for å fjerne små gap før topologibygging,20151103,knjetl,Endred SurfaceDraper til Vertex og Constant, for å unngå nye punkt i OSM-linjer,20151103,knjetl,Group by medium på Anchored Snapper, for å unngå snapping mellom OSM-undergang og kryssende veg

Parameters:
- Knr = 403   # Kommunenummer
- mDir = O:\Landsdekkende\Geodata\Spesialleveranser\Sykkeldatasett\Data\Kommunevise   # Hovedmappe
- OSMfile = C:\DATA\Sykkelreiseplanlegger\Data\OSM\Norge_UTM33_Validated.sl3   # File
- TNE_sl3 = C:\DATA\TNE\data\tne_local.db   # Lokal TNE
- xfmap_api = \\client\C$\DATA\Sykkelreiseplanlegger\FMW\API_Mapping.xmp   # xfMap for API-mapping
- LOG_FILE = $(mDir)\Sykkeldata_$(Knr).log   # Log File
- coordsys = EPSG:25833   # Koordinatsystem
- lokasjonstype = kommune   # Lokasjonstype

Writers:
- SPATIALITE_1: SPATIALITE to $(mDir) in EPSG:25833

TestFilter_IkkeBygning_-__TestFilter_IkkeBygning: Junction
    -> AnchoredSnapper_2 [ANCHOR]
    -> TestFilter_IkkeBygning_2
Note: Topologirydding : Frinavigeringssoner
TestFilter_IkkeBygning_2: Junction
    -> Topologirydding_Frinavigeringssoner
curvesegment: Inspector [off]
Note: Skiller mellom lenker fra NVDB og OSM. / Kun NVDB-lenker skal brukes i LR-tilknytning
AttributeFilter_2
    ATTR_NAME = kilde
    ATTR_VALUES = OSM,NVDB,<EMPTY>,<MISSING>,<NULL>,<BLANK>,<UNFILTERED>
    OSM -> AnchoredSnapper_2_SNAPPED_-__NullAttributeMapper_2_Output_-__NullAttributeMapper_2
    NVDB -> EventGeometry [Network]
EventGeometry
    _eventFrom = @Value(FROM_MEASURE)
    _rlFrom = @Value(FROM_MEASURE)
    _eventRouteID = @Value(ROUTE_ID)
    _rlRouteID = @Value(REFLINK_OID)
    _eventTo = @Value(TO_MEASURE)
    _measureMode = 3D
    _rlTo = @Value(TO_MEASURE)
    _dimension = 3
    Lines -> TestFilter_7
AnchoredSnapper_2_SNAPPED_-__NullAttributeMapper_2_Output_-__NullAttributeMapper_2: Junction
    -> NullAttributeMapper_2

Bookmark: Utvalg (antall kommuner og nummer)
Creator_3
    GEOMTYPE = Geometry Object
    NUM = 1
    CREATED -> Counter_2
Counter_2
    SCOPE = Global
    START = $(Knr)
    DOMAIN = counter
    CNT_ATTR = _count
    -> HTTPCaller_4

Bookmark: Leser Kommuneflate fra NVDB API
Note: Henter objekter fra NVDB-API
HTTPCaller_4
    TARGET_ATTR = _url_contents
    ERROR_ATTR = _error
    SAVE_FILE = Attribute
    RESPONSE_HEADER_LIST_ATTR = _headers
    VERIFY_SSL_CERTIFICATES = Yes
    TRANSFER_TIMEOUT_LENGTH = 90
    STATUS_CODE_ATTR = _http_status_code
    CONNECTION_TIMEOUT_LENGTH = 60
    USE_COOKIES = No
    TARGET_ATTR_ENCODING = auto-detect
    HTTP_METHOD = GET
    TARGET_URL = https://www.vegvesen.no/nvdb/api/sok?kriterie={"lokasjon":{"$(lokasjonstype)":["@Value(_count)"]},"objektTyper":[{"id":536,"antall":"100000","filter":[]}]}
    FOLLOW_REDIRECTS = Yes
    CUSTOM_HEADERS = Accept;application/vnd.vegvesen.nvdb-v1+xml
    -> XMLFeatureMapper_3
Note: Tolker XML
XMLFeatureMapper_3
    SINGLE_XFMAP = $(xfmap_api)
    XML_INPUT_TYPE = Attribute with XML document
    CONFIGURATION_TYPE = Single xfMap file
    MERGE_ATTRS = Yes
    ATTRIBUTE_XML = _url_contents
    XML_SOURCE_NAME = _xml_source_
    FEATURE_TYPE_ATTR = fme_feature_type
    NEW_ATTRIBUTES = egengeometri geometriUtm33 vegreferanse{}.vegkategori vegreferanse{}.vegnummer vegreferanse{}.vegstatus vegreferanse{}.hovedParsell vegreferanse{}.veglenkeMeterFra vegreferanse{}.veglenkeMeterTil lineærPosisjon{}.lineærtObjektIdentifikasjon.Identifikasjon.lokalId lineærPosisjon{}.fraPosisjon lineærPosisjon{}.tilPosisjon lineærPosisjon{}.felt vegreferanse{}.fylke vegreferanse{}.kommune NVDB_ID
    FEATURE_COUNT_PER_XML = _xml_feature_count_
    MAPPED -> GeometryReplacer_3
Note: Tildeler geometri
GeometryReplacer_3
    KIND_LONG = OGC Well Known Text
    OGC_WKT_PRECISION_DISPLAY = 64-bit
    SOURCE = @Value(geometriUtm33)
    REMOVE_ATTRIBUTE = Yes
    -> CoordinateSystemSetter_3
CoordinateSystemSetter_3
    COORDSYS = $(coordsys)
    -> Dissolver_2
Dissolver_2
    NO_OVRLP = No
    CONNECT_Z_MODE = First Wins
    ACCUM_INPUT_ATTRS = Drop Incoming Attributes
    GROUP_BY = _count
    AREA -> DonutHoleExtractor
DonutHoleExtractor
    OUTERSHELL -> TimeStamper_2
    OUTERSHELL -> FeatureReader_5 [INITIATOR]
    OUTERSHELL -> Clipper [CLIPPER]

Bookmark: Leser forhåndsprosessert OSM
Note: Relevante objekttyper
FeatureReader_5
    DATASET = $(OSMfile)
    ATTR_ACCUM_MODE = Only Use Result
    COMBINE_GEOM = Use Result
    FORMAT = SPATIALITE
    SUPPORTED_SPATIAL_INTERACTIONS = ENVELOPE_INTERSECT%INTERSECTS%CONTAINS%CROSSES%DISJOINT%EQUALS%OVERLAPS%TOUCHES%WITHIN
    SPATIALITE_QUERY_FEATURE_TYPES_FOR_MERGE_FILTERS = Yes
    OUTPUT_FEATURES_DISPLAY = Schema and Data Features
    ATTRIBUTES = bygninger,"building,shop",frinavigeringssoner,"navn,type",lenker,"typeveg,vegnavn,medium,trafikkretning,andel_lange,kilde,belysning,aadt,startnode,fartsgrense,sykkelforbud,sluttnode"
    FEATURETYPES = bygninger frinavigeringssoner lenker
    INTERACT = Intersects
    bygninger -> AttributeCreator
    frinavigeringssoner -> AreaOnAreaOverlayer [AREA]
    lenker -> GeometryFilter_3

Bookmark: Identifiserer parkeringsplasser, torg og fotgjengerområder, og klipper mot bygninger --> frinavigeringssoner
AttributeCreator
    ATTR_TABLE = SET_TO Bygning = Ja
    -> AreaOnAreaOverlayer [AREA]
Note: Klipper mot bygninger
AreaOnAreaOverlayer
    CONNECT_Z_MODE = First Wins
    OVC_ATTR = _overlaps
    ACCUM_ATTRS_NAME = Merge Incoming Attributes
    AREA -> TestFilter
Note: Fjerner bygninger fra sonene
TestFilter
    TEST_LIST = BOOL_OP,OR,COMPOSITE_TEST,<Unused>,TEST_CLAUSE,"TEST @Value(Bygning) != Ja",IkkeBygning
    DEFAULT_VALUE = <UNFILTERED>
    IkkeBygning -> Bufferer
    IkkeBygning -> TestFilter_IkkeBygning_-__TestFilter_IkkeBygning
Note: Legger på en liten buffer, for å sikre overlapp med lenker inn til sonen
Bufferer
    CAP_STYLE = Round
    OFFSET = 0.5
    INTERP_SEGMENTS = 8
    BUFFERED -> frinavigeringssoner (writer SPATIALITE_1)
frinavigeringssoner (writer SPATIALITE_1)
    attributes: navn string(30), type string(30)

Bookmark: Bygger topologi
Note: TestFilter : IkkeBygning
Topologirydding_Frinavigeringssoner: Junction
    -> Topologirydding [Frinavigeringssoner]
NullAttributeMapper_2
    ATTRCHOICE = Selected Attributes
    NEW_VALUE = T
    ATTRLIST = medium
    SOURCE_ATTR_VAL = Null Empty "Missing (Selected Attributes Only)"
    NULL_TREATMENT = New Value
    -> GeometryValidator
GeometryValidator
    NULL_REMOVAL = NULL_REMOVAL
    ISSUE_ATTR_NAME = _issues
    REPAIR = Yes
    ARC_ENDPOINT_TOLERANCE_MODE = Auto
    PRESETS = Basic Geometry Integrity
    NAN_REMOVAL = NAN_REMOVAL
    SUMMARY = Detailed
    CONNECT_Z_MODE_TR = First Wins
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    TYPE_REPAIR = TYPE_REPAIR
    PASSED -> Snapper
    REPAIRED -> Snapper
Note: Fjerner små gap
Snapper
    SNAPTYPE_PARAM = Segment Snapping
    TOLERANCE = 0.15
    GROUP_BY = medium
    SNAPPED -> TopologyBuilder_3
    UNTOUCHED -> TopologyBuilder_3
Note: Bygger topologi. Grupperer på medium, og tillater nye noder. Dette for å koble NVDB- og OSM-data
TopologyBuilder_3
    DEAGGREGATE_INPUT = Yes
    MAX = 0
    CLEAN_DATA = No
    BOUNDING_EDGES = All
    ALLOW_CYCLES = No
    OVERLAPPING_MODE = No
    PROP_ATTRS = No
    GROUP_BY = medium
    NODE -> TopologyBuilder_2
    LINE -> TopologyBuilder_2
Note: Bygger topologi med nye lenker og noder, skiller ikke på medium. / Bruker "assume clean data", for å unngå nye noder
TopologyBuilder_2
    DEAGGREGATE_INPUT = Yes
    MAX = 0
    CLEAN_DATA = Yes
    BOUNDING_EDGES = All
    ALLOW_CYCLES = No
    OVERLAPPING_MODE = No
    PROP_ATTRS = No
    NODE -> Topologirydding [Noder]
    LINE -> Topologirydding [Lenker]
Note: Fjerner gap i geometrien
Topologirydding
    dXYlim = 5
    __COMPOUND_PARAMETERS = -
    Lenker -> AttributeExposer
AttributeExposer
    ATTR_LIST = typeveg,vegnavn,sykkelforbud,trafikkretning,aadt,andel_lange,belysning,farstgrense,medium,kilde
    -> CoordinateRounder_2
CoordinateRounder_2
    ZPREC = 1
    YPREC = 1
    XPREC = 1
    ROUNDED -> GeometryValidator_2
GeometryValidator_2
    NULL_REMOVAL = NULL_REMOVAL
    ISSUE_ATTR_NAME = _issues
    REPAIR = Yes
    ARC_ENDPOINT_TOLERANCE_MODE = Auto
    PRESETS = Basic Geometry Integrity
    NAN_REMOVAL = NAN_REMOVAL
    SUMMARY = Detailed
    CONNECT_Z_MODE_TR = First Wins
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    TYPE_REPAIR = TYPE_REPAIR
    PASSED -> TopologyBuilder_4
    REPAIRED -> TopologyBuilder_4
Note: Bygger topologi med nye lenker, skiller ikke på medium. / Bruker "assume clean data", for å unngå nye noder
TopologyBuilder_4
    DEAGGREGATE_INPUT = Yes
    MAX = 0
    CLEAN_DATA = Yes
    BOUNDING_EDGES = All
    ALLOW_CYCLES = No
    OVERLAPPING_MODE = No
    PROP_ATTRS = No
    NODE -> AttributeRenamer_8
    LINE -> AttributeRenamer_6
AttributeRenamer_8
    ATTR_TABLE = RENAME_SET_DEFAULT _node_number > nodeid
    -> noder (writer SPATIALITE_1)
Note: noder
noder (writer SPATIALITE_1)
    attributes: nodeid string(20)
AttributeRenamer_6
    ATTR_TABLE:
      RENAME_SET_DEFAULT _from_node > startnode
      RENAME_SET_DEFAULT _to_node > sluttnode
    -> GeometryExtractor
NullAttributeMapper
    ATTRCHOICE = Selected Attributes
    NEW_VALUE = Nei
    ATTRLIST = sykkelforbud belysning
    SOURCE_ATTR_VAL = Empty "Missing (Selected Attributes Only)" Null
    NULL_TREATMENT = New Value
    -> StringCaseChanger
Note: STORE BOKSTAVER i vegnavn
StringCaseChanger
    ATTRCHOICE = Selected Attributes
    ATTRLIST = vegnavn
    CHANGE_TYPE = UPPERCASE
    -> lenker (writer SPATIALITE_1)
    -> lenker
lenker: Inspector [off]
    TACKATTRS = kilde
Note: lenker
lenker (writer SPATIALITE_1)
    attributes: typeveg string(2), vegnavn string(50), sykkelforbud string(5), trafikkretning string(10), aadt string(20), andel_lange string(10), belysning string(5), fartsgrense string(20), startnode string(20), sluttnode string(20), medium string(5), kilde string(5)

Bookmark: Finner aktueller lenker fra OpenStreetMap og klipper mot kommunegrense
GeometryFilter_3
    BREAK_AGG = No
    GEOM_PORT_NAMES = Line
    LINE -> Clipper [CLIPPEE]
Note: Klipper mot kommunegrenser
Clipper
    CLIP_TYPE = Multiple Clippers
    CONNECT_Z_MODE = First Wins
    CLIPPED_ATTR = _clipped
    CREATE_AGGREGATES = Yes
    BOUNDARY_CASES = Treat as Inside
    PRESERVE_CLIPPEE_EXTENTS = No
    LINES_AS_SEGMENTS = No
    INSIDE -> AttributeCreator_6
AttributeCreator_6
    ATTR_TABLE:
      SET_TO sykkelforbud = Nei
      SET_TO kilde = OSM
    -> 2DForcer
2DForcer
    2D -> AnchoredSnapper [CANDIDATE]

Bookmark: Vegnett og fagdata fra TNE og NVDB API
TimeStamper_2
    TIME_ATTR = _timestamp
    FMT = FME Date (^Y^m^d)
    -> StringConcatenator_2
    -> StringConcatenator_5
StringConcatenator_5
    PARM_LINE = TO_DATE>@Value(_timestamp) AND CLASS_CODE <> 7012
    VAL_ATTR = _where
    ACTION = Create New Attribute
    -> FeatureReader_3 [INITIATOR]
Note: Leser vegnettsgeometri fra TNE / (Alt unntatt Vegtrase)
FeatureReader_3
    DATASET = $(TNE_sl3)
    ATTR_ACCUM_MODE = Only Use Result
    COMBINE_GEOM = Use Result
    WHERE = @Value(_where)
    FORMAT = SPATIALITE
    SUPPORTED_SPATIAL_INTERACTIONS = ENVELOPE_INTERSECT%ENVELOPE_INTERSECT%INTERSECTS%CONTAINS%CROSSES%DISJOINT%EQUALS%OVERLAPS%TOUCHES%WITHIN
    SPATIALITE_QUERY_FEATURE_TYPES_FOR_MERGE_FILTERS = Yes
    OUTPUT_FEATURES_DISPLAY = Schema and Data Features
    ATTRIBUTES = belysningsanlegg,"objectid,netobjecttv_id,from_date,to_date,seq_no,ba_200026_oid,ba_200246_oid,ba_200558_oid,ba_201440_oid,brom_1271,type_1144,navns_8396,bygge_8399,tenns_8404,mast_3700,lost_3697,stfb_3755,stve_3760,eier_5810,eiern_8397,vhan_1554,jevnk_8743,lumkr_8740,avin_1714,tilsk_8398,utedr_8400,vdb_i_7656,route_id,from_measure,to_measure,side,topology_level,dimmi_10001,shape_len",bruksklasse,"objectid,netobjecttv_id,from_date,to_date,seq_no,ba_200239_oid,bk_5179,bkvin_5180,bktel_5181,akste_7576,mvgl_5186,brsp_5184,strbe_5183,strsp_8800,strto_8801,beskr_9308,beskr_9309,merk_5182,vektm_9125,lengm_9126,vektt_9127,lengt_9128,t100tv_9254,mobkr_9256,maxle_8804,kjtle_8805,maxto_7542,maxto_7577,maxto_7578,maxto_7579,vdb_i_7670,route_id,from_measure,to_measure,topology_level,strbe_10721,mvvin_10722,mvlin_10723,shape_len",curvesegment,"objectid,reflink_oid,from_date,to_date,from_measure,to_measure,seg_date,length,class_code,object_code,medium,quality_method,quality_accuracy,quality_visibility,quality_method_height,quality_accuracy_height,quality_tolerance,municipality,shape_len",fartsgrense,"objectid,netobjecttv_id,from_date,to_date,seq_no,ba_200272_oid,ba_200952_oid,ba_201829_oid,fagr_2021,vtnr_1891,vtdt_5124,journ_9155,vrfg_5125,gfdt_5127,tidb_2071,vdb_i_7671,route_id,from_measure,to_measure,lanecode,topology_level,shape_len",feltstrekning,"objectid,netobjecttv_id,from_date,to_date,seq_no,flto_5528,route_id,from_measure,to_measure,topology_level,shape_len",fortau,"objectid,netobjecttv_id,from_date,to_date,seq_no,ba_200235_oid,ba_200280_oid,ba_200569_oid,ba_201418_oid,ba_201692_oid,vhan_5638,eier_7994,bel_5637,vdb_i_7633,vaka_1830,route_id,from_measure,to_measure,side,topology_level,ba_202020_oid,bygge_10295,bredg_2241,bredh_10717,punkt_10718,ba_202126_oid,shape_len",gate,"objectid,netobjecttv_id,from_date,to_date,seq_no,ht_200699_oid,ba_201568_oid,gtkd_4588,gtnv_4589,route_id,from_measure,to_measure,side,topology_level,sidev_9793,shape_len",ikfb,"objectid,netobjecttv_id,from_date,to_date,seq_no,ba_200801_oid,mrk_5476,sknr_5475,route_id,from_measure,to_measure,side,direction,lanecode,topology_level,shape_len",motorveg,"objectid,netobjecttv_id,from_date,to_date,seq_no,ba_200790_oid,mvegt_5378,vtakd_5377,vedta_5376,route_id,from_measure,to_measure,topology_level,journ_9485,bygge_10328,shape_len",trafikkmengde,"objectid,netobjecttv_id,from_date,to_date,seq_no,ba_200670_oid,ba_201812_oid,tadt_4623,langx_4624,ar_4621,opfr_6843,grlg_4625,anid_4620,trafa_7477,tppm_5219,tpsd_5222,fadt_5220,flng_5221,kpar_5223,mfak_4622,aadts_7475,aadts_7476,vdb_i_7804,route_id,from_measure,to_measure,topology_level,shape_len",tunnel,"objectid,netobjecttv_id,from_date,to_date,seq_no,ba_200710_oid,ba_200711_oid,ba_200714_oid,ba_200752_oid,ba_200778_oid,ba_200785_oid,navn_5225,tunne_9306,tunne_9134,parhl_3947,lensk_8945,lenlo_8150,lenra_8151,under_9517,sykke_9518,tlfvt_3917,albra_3918,kbsn_3915,kbng_3916,brann_9507,restr_9131,mrkre_9506,mksy_3913,brutu_9329,route_id,measure,topology_level,xlht_3947,bpgk_3919,bplan_9132,upba_3914,sngt_3917,avfb_3918,apnea_10383,ba_202110_oid",tunnellop,"objectid,netobjecttv_id,from_date,to_date,seq_no,kateg_8944,tunlp_1977,type_1130,leng_1317,area_1367,bred_3897,apnin_8356,usjo_5272,skfb_3899,innbe_7864,brutu_9305,innr_2178,merk_5286,vdb_i_7642,ba_200031_oid,ba_200061_oid,ba_200167_oid,ba_200187_oid,ba_200201_oid,ba_200202_oid,ba_200203_oid,ba_200205_oid,ba_200407_oid,ba_200464_oid,ba_200739_oid,ba_200740_oid,ba_200741_oid,ba_200742_oid,ba_200743_oid,ba_200744_oid,ba_200745_oid,ba_200746_oid,ba_200747_oid,ba_200749_oid,ba_200751_oid,ba_200755_oid,ba_200757_oid,ba_200759_oid,ba_200760_oid,ba_200761_oid,ba_200762_oid,ba_200763_oid,ba_200764_oid,ba_200765_oid,ba_200766_oid,ba_200767_oid,ba_200768_oid,ba_200769_oid,ba_200770_oid,ba_200772_oid,ba_200774_oid,ba_200775_oid,ba_200776_oid,ba_200777_oid,ba_200779_oid,ba_200781_oid,ba_200782_oid,ba_200784_oid,ba_200786_oid,ba_200811_oid,ba_200812_oid,ba_200813_oid,ba_200815_oid,ba_200816_oid,ba_200817_oid,ba_200818_oid,ba_200819_oid,ba_200839_oid,ba_201427_oid,ba_201637_oid,ba_201815_oid,ba_201819_oid,ba_201830_oid,ba_201833_oid,ba_201868_oid,ba_201869_oid,ba_201874_oid,ba_201877_oid,ba_201878_oid,navn_1081,route_id,from_measure,to_measure,side,lanecode,topology_level,ba_201885_oid,ba_201893_oid,ba_201894_oid,ba_200081_oid,ba_201971_oid,ba_202006_oid,ba_202035_oid,ba_202041_oid,ba_202042_oid,ba_202046_oid,ba_202038_oid,ba_202039_oid,ba_202083_oid,ba_202103_oid,rehab_10693,shape_len",vegfunksjon,"objectid,netobjecttv_id,from_date,to_date,seq_no,ba_200705_oid,vf_5178,route_id,from_measure,to_measure,topology_level,shape_len",vegreferanse,"objectid,netobjecttv_id,from_date,to_date,seq_no,fynr_4591,kmnr_4592,vktg_4566,vsov_4570,vgnr_4568,hp_4569,vsts_4567,frmt_4571,tlmt_4572,brk1_4576,brk2_4577,vgtp_4574,fvkd_4573,enrg_4707,svtp_4575,mdat_4578,route_id,from_measure,to_measure,direction,topology_level,shape_len"
    FEATURETYPES = curvesegment
    INTERACT = Intersects
    curvesegment -> BulkAttributeRenamer
    curvesegment -> curvesegment
BulkAttributeRenamer
    CASE_CHANGE_TYPE = upper
    ATTRCHOICE = All Attributes
    MODE_CHOICE = RENAME
    PATTERN_ACTION_DISP = CASECHANGE
    -> AttributeValueMapper_4
AttributeValueMapper_4
    SRC = CLASS_CODE
    VAL_ATTR = OBJTYPE
    LUT = 6304,FrittståendeTrapp,7001,VegSenterlinje,7004,Svingekonnekteringslenke,7010,Kjørefelt,7011,Kjørebane,7012,Vegtrase,7042,GangSykkelVegSenterlinje,7046,Fortau,7201,Bilferjestrekning,7043,Sykkelveg
    DIRECTION = Forward (Source To Destination)
    -> AttributeManager
AttributeManager
    ATTR_TABLE:
      REMOVE OBJECTID
      REMOVE FROM_DATE
      REMOVE TO_DATE
      REMOVE SEG_DATE
      REMOVE LENGTH
      REMOVE CLASS_CODE
      REMOVE OBJECT_CODE
      RENAME_SET_VALUE MEDIUM > TNE_MEDIUM
      REMOVE QUALITY_METHOD
      REMOVE QUALITY_ACCURACY
      REMOVE QUALITY_VISIBILITY
      REMOVE QUALITY_METHOD_HEIGHT
      REMOVE QUALITY_ACCURACY_HEIGHT
      REMOVE QUALITY_TOLERANCE
      REMOVE MUNICIPALITY
      REMOVE SHAPE_LEN
      SET_TO kilde = NVDB
    -> AttributeValueMapper
Note: Konverterer / TNE-MEDIUM-verdier
AttributeValueMapper
    SRC = TNE_MEDIUM
    VAL_ATTR = medium
    LUT = 0,T,1,B,2,L,3,U
    DIRECTION = Forward (Source To Destination)
    DEFAULT_VALUE = T
    -> LineVertexElevationCorrector [Input_lines]
    -> AnchoredSnapper [ANCHOR]
Note: Lager where-setning for / gyldige data og topologinivå / VTKB, KB eller KF
StringConcatenator_2
    PARM_LINE = TO_DATE>@Value(_timestamp) AND TOPOLOGY_LEVEL>0
    VAL_ATTR = _where
    ACTION = Create New Attribute
    -> Sykkelforbud [Område]
    -> FeatureReader_4 [INITIATOR]
Note: Bruker NVDB-API og TNE for å finne tunnelløp med sykkelforbud. Kombinerer med motorveg
Sykkelforbud
    TNE_sl3 = $(TNE_sl3)
    Sykkelforbud -> Segmentering [Sykkelforbud]
Note: Fagdata fra TNE
FeatureReader_4
    DATASET = $(TNE_sl3)
    ATTR_ACCUM_MODE = Only Use Result
    COMBINE_GEOM = Use Result
    WHERE = @Value(_where)
    FORMAT = SPATIALITE
    SUPPORTED_SPATIAL_INTERACTIONS = ENVELOPE_INTERSECT%ENVELOPE_INTERSECT%INTERSECTS%CONTAINS%CROSSES%DISJOINT%EQUALS%OVERLAPS%TOUCHES%WITHIN
    SPATIALITE_QUERY_FEATURE_TYPES_FOR_MERGE_FILTERS = Yes
    OUTPUT_FEATURES_DISPLAY = Schema and Data Features
    ATTRIBUTES = belysningsanlegg,"objectid,netobjecttv_id,from_date,to_date,seq_no,ba_200026_oid,ba_200246_oid,ba_200558_oid,ba_201440_oid,brom_1271,type_1144,navns_8396,bygge_8399,tenns_8404,mast_3700,lost_3697,stfb_3755,stve_3760,eier_5810,eiern_8397,vhan_1554,jevnk_8743,lumkr_8740,avin_1714,tilsk_8398,utedr_8400,vdb_i_7656,route_id,from_measure,to_measure,side,topology_level,dimmi_10001,shape_len",bruksklasse,"objectid,netobjecttv_id,from_date,to_date,seq_no,ba_200239_oid,bk_5179,bkvin_5180,bktel_5181,akste_7576,mvgl_5186,brsp_5184,strbe_5183,strsp_8800,strto_8801,beskr_9308,beskr_9309,merk_5182,vektm_9125,lengm_9126,vektt_9127,lengt_9128,t100tv_9254,mobkr_9256,maxle_8804,kjtle_8805,maxto_7542,maxto_7577,maxto_7578,maxto_7579,vdb_i_7670,route_id,from_measure,to_measure,topology_level,strbe_10721,mvvin_10722,mvlin_10723,shape_len",curvesegment,"objectid,reflink_oid,from_date,to_date,from_measure,to_measure,seg_date,length,class_code,object_code,medium,quality_method,quality_accuracy,quality_visibility,quality_method_height,quality_accuracy_height,quality_tolerance,municipality,shape_len",fartsgrense,"objectid,netobjecttv_id,from_date,to_date,seq_no,ba_200272_oid,ba_200952_oid,ba_201829_oid,fagr_2021,vtnr_1891,vtdt_5124,journ_9155,vrfg_5125,gfdt_5127,tidb_2071,vdb_i_7671,route_id,from_measure,to_measure,lanecode,topology_level,shape_len",feltstrekning,"objectid,netobjecttv_id,from_date,to_date,seq_no,flto_5528,route_id,from_measure,to_measure,topology_level,shape_len",fortau,"objectid,netobjecttv_id,from_date,to_date,seq_no,ba_200235_oid,ba_200280_oid,ba_200569_oid,ba_201418_oid,ba_201692_oid,vhan_5638,eier_7994,bel_5637,vdb_i_7633,vaka_1830,route_id,from_measure,to_measure,side,topology_level,ba_202020_oid,bygge_10295,bredg_2241,bredh_10717,punkt_10718,ba_202126_oid,shape_len",gate,"objectid,netobjecttv_id,from_date,to_date,seq_no,ht_200699_oid,ba_201568_oid,gtkd_4588,gtnv_4589,route_id,from_measure,to_measure,side,topology_level,sidev_9793,shape_len",ikfb,"objectid,netobjecttv_id,from_date,to_date,seq_no,ba_200801_oid,mrk_5476,sknr_5475,route_id,from_measure,to_measure,side,direction,lanecode,topology_level,shape_len",motorveg,"objectid,netobjecttv_id,from_date,to_date,seq_no,ba_200790_oid,mvegt_5378,vtakd_5377,vedta_5376,route_id,from_measure,to_measure,topology_level,journ_9485,bygge_10328,shape_len",trafikkmengde,"objectid,netobjecttv_id,from_date,to_date,seq_no,ba_200670_oid,ba_201812_oid,tadt_4623,langx_4624,ar_4621,opfr_6843,grlg_4625,anid_4620,trafa_7477,tppm_5219,tpsd_5222,fadt_5220,flng_5221,kpar_5223,mfak_4622,aadts_7475,aadts_7476,vdb_i_7804,route_id,from_measure,to_measure,topology_level,shape_len",tunnel,"objectid,netobjecttv_id,from_date,to_date,seq_no,ba_200710_oid,ba_200711_oid,ba_200714_oid,ba_200752_oid,ba_200778_oid,ba_200785_oid,navn_5225,tunne_9306,tunne_9134,parhl_3947,lensk_8945,lenlo_8150,lenra_8151,under_9517,sykke_9518,tlfvt_3917,albra_3918,kbsn_3915,kbng_3916,brann_9507,restr_9131,mrkre_9506,mksy_3913,brutu_9329,route_id,measure,topology_level,xlht_3947,bpgk_3919,bplan_9132,upba_3914,sngt_3917,avfb_3918,apnea_10383,ba_202110_oid",tunnellop,"objectid,netobjecttv_id,from_date,to_date,seq_no,kateg_8944,tunlp_1977,type_1130,leng_1317,area_1367,bred_3897,apnin_8356,usjo_5272,skfb_3899,innbe_7864,brutu_9305,innr_2178,merk_5286,vdb_i_7642,ba_200031_oid,ba_200061_oid,ba_200167_oid,ba_200187_oid,ba_200201_oid,ba_200202_oid,ba_200203_oid,ba_200205_oid,ba_200407_oid,ba_200464_oid,ba_200739_oid,ba_200740_oid,ba_200741_oid,ba_200742_oid,ba_200743_oid,ba_200744_oid,ba_200745_oid,ba_200746_oid,ba_200747_oid,ba_200749_oid,ba_200751_oid,ba_200755_oid,ba_200757_oid,ba_200759_oid,ba_200760_oid,ba_200761_oid,ba_200762_oid,ba_200763_oid,ba_200764_oid,ba_200765_oid,ba_200766_oid,ba_200767_oid,ba_200768_oid,ba_200769_oid,ba_200770_oid,ba_200772_oid,ba_200774_oid,ba_200775_oid,ba_200776_oid,ba_200777_oid,ba_200779_oid,ba_200781_oid,ba_200782_oid,ba_200784_oid,ba_200786_oid,ba_200811_oid,ba_200812_oid,ba_200813_oid,ba_200815_oid,ba_200816_oid,ba_200817_oid,ba_200818_oid,ba_200819_oid,ba_200839_oid,ba_201427_oid,ba_201637_oid,ba_201815_oid,ba_201819_oid,ba_201830_oid,ba_201833_oid,ba_201868_oid,ba_201869_oid,ba_201874_oid,ba_201877_oid,ba_201878_oid,navn_1081,route_id,from_measure,to_measure,side,lanecode,topology_level,ba_201885_oid,ba_201893_oid,ba_201894_oid,ba_200081_oid,ba_201971_oid,ba_202006_oid,ba_202035_oid,ba_202041_oid,ba_202042_oid,ba_202046_oid,ba_202038_oid,ba_202039_oid,ba_202083_oid,ba_202103_oid,rehab_10693,shape_len",vegfunksjon,"objectid,netobjecttv_id,from_date,to_date,seq_no,ba_200705_oid,vf_5178,route_id,from_measure,to_measure,topology_level,shape_len",vegreferanse,"objectid,netobjecttv_id,from_date,to_date,seq_no,fynr_4591,kmnr_4592,vktg_4566,vsov_4570,vgnr_4568,hp_4569,vsts_4567,frmt_4571,tlmt_4572,brk1_4576,brk2_4577,vgtp_4574,fvkd_4573,enrg_4707,svtp_4575,mdat_4578,route_id,from_measure,to_measure,direction,topology_level,shape_len"
    FEATURETYPES = belysningsanlegg fartsgrense feltstrekning fortau gate ikfb trafikkmengde vegreferanse
    INTERACT = Envelope Intersects
    <SCHEMA> -> BulkAttributeRenamer_2
    belysningsanlegg -> BulkAttributeRenamer_2
    fartsgrense -> BulkAttributeRenamer_2
    feltstrekning -> BulkAttributeRenamer_2
    fortau -> BulkAttributeRenamer_2
    gate -> BulkAttributeRenamer_2
    ikfb -> BulkAttributeRenamer_2
    trafikkmengde -> BulkAttributeRenamer_2
    vegreferanse -> BulkAttributeRenamer_2
BulkAttributeRenamer_2
    CASE_CHANGE_TYPE = upper
    ATTRCHOICE = All Attributes
    MODE_CHOICE = RENAME
    PATTERN_ACTION_DISP = CASECHANGE
    -> AttributeExposer_2
AttributeExposer_2
    ATTR_LIST = fme_feature_type
    -> AttributeFilter_3
AttributeFilter_3
    ATTR_NAME = fme_feature_type
    ATTR_VALUES = <EMPTY>,<MISSING>,<NULL>,<UNFILTERED>,belysningsanlegg,fortau,ikfb,trafikkmengde,gate,feltstrekning,fartsgrense,vegreferanse
    belysningsanlegg -> Segmentering [Belysning]
    fortau -> Segmentering [Fortau]
    ikfb -> Segmentering [InnkjøringForbudt]
    trafikkmengde -> Segmentering [Trafikkmengde]
    gate -> Segmentering [Gate]
    feltstrekning -> Segmentering [Feltstrekning]
    fartsgrense -> Segmentering [Fartsgrense]
    vegreferanse -> Segmentering [Vegreferanse]
Segmentering
    Segmenter -> StringFormatter
Note: Avrunder til 8 desimaler
StringFormatter
    SRC_ATTRS = FROM_MEASURE,TO_MEASURE
    FORMAT = .8f
    -> TestFilter_3

Bookmark: Snapper OSM-lenker til NVDB-lenker og frinavigeringssoner
Note: Snapper OSM-lenker til NVDB-lenker
AnchoredSnapper
    SNAPTYPE_PARAM = Segment Snapping
    TOLERANCE = 2
    GROUP_BY = medium
    SNAPPED -> AnchoredSnapper_2 [CANDIDATE]
    UNTOUCHED -> AnchoredSnapper_2 [CANDIDATE]
Note: Snapper OSM-lenker til frinavigeringssoner
AnchoredSnapper_2
    SNAPTYPE_PARAM = Segment Snapping
    TOLERANCE = 1
    SNAPPED -> LineVertexElevationCorrector [Input_lines]
    UNTOUCHED -> LineVertexElevationCorrector [Input_lines]

Bookmark: Oppretting av høydeverdier (både NVDB og OSM)
Note: Interpolerer høyder på / enkeltpunkt uten høyde i linjer med høyde
LineVertexElevationCorrector
    NullLimit = -500
    NoElevation -> ElevationInterpolator
    Lines_with_elevation -> ElevationInterpolator
Note: Interpolerer høyde på 2d-linjer
ElevationInterpolator
    -> AttributeFilter_2

Bookmark: Type veg
TestFilter_3
    TEST_LIST:
      BOOL_OP,OR,COMPOSITE_TEST,<Unused>,TEST_CLAUSE,"TEST ""@Value(VSTS_4567)"" = ""5499""
      TEST ""@Value(VSTS_4567)"" = ""5505""
      TEST ""@Value(VSTS_4567)"" = ""5502""
      TEST ""@Value(VSTS_4567)"" = ""7041""
      TEST ""@Value(VSTS_4567)"" = ""5501""",VEG,BOOL_OP,OR,COMPOSITE_TEST,<Unused>,TEST_CLAUSE,"TEST ""@Value(VSTS_4567)"" = ""5504""",FERJE,BOOL_OP,OR,COMPOSITE_TEST,<Unused>,TEST_CLAUSE,"TEST ""@Value(VSTS_4567)"" = ""12159""
      TEST ""@Value(VSTS_4567)"" = ""12160""
      TEST ""@Value(VSTS_4567)"" = ""12983""",GSVEG
    DEFAULT_VALUE = <UNFILTERED>
    VEG -> AttributeValueMapper_3
    FERJE -> AttributeCreator_14
    GSVEG -> AttributeCreator_13
Note: typeveg ut fra vegkategori
AttributeValueMapper_3
    SRC = VKTG_4566
    VAL_ATTR = typeveg
    LUT = 5492,Europaveg,5493,Riksveg,5494,Fylkesveg,5495,Kommunal veg,5496,Privat veg,5497,Skogsbilveg
    DIRECTION = Forward (Source To Destination)
    -> AttributeRenamer_3

Bookmark: Vegnavn
Note: GATENAVN --> VEGNAVN
AttributeRenamer_3
    ATTR_TABLE = RENAME_SET_DEFAULT GTNV_4589 > vegnavn
    -> TestFilter_4
TestFilter_4
    TEST_LIST:
      BOOL_OP,AND,COMPOSITE_TEST,<Unused>,TEST_CLAUSE,"TEST ""@Value(HP_4569)"" >= ""400""
      TEST ""@Value(HP_4569)"" < ""500""",RUNDKJØRING
    DEFAULT_VALUE = <UNFILTERED>
    RUNDKJØRING -> AttributeCreator_3
    <UNFILTERED> -> TestFilter_5
Note: Vegnavn = / "RUNDKJØRING"
AttributeCreator_3
    ATTR_TABLE = SET_TO vegnavn = Rundkjøring
    -> AttributeCreator_3_OUTPUT_-__AttributeFilter
AttributeCreator_3_OUTPUT_-__AttributeFilter: Junction
    -> AttributeFilter
TestFilter_5
    TEST_LIST = BOOL_OP,OR,COMPOSITE_TEST,<Unused>,TEST_CLAUSE,"TEST ""@Value(VKTG_4566)"" = ""5492""",E,BOOL_OP,OR,COMPOSITE_TEST,<Unused>,TEST_CLAUSE,"TEST ""@Value(VKTG_4566)"" = ""5493""",R,BOOL_OP,OR,COMPOSITE_TEST,<Unused>,TEST_CLAUSE,"TEST ""@Value(VKTG_4566)"" = ""5494""",F
    DEFAULT_VALUE = <UNFILTERED>
    E -> StringConcatenator_3
    R -> StringConcatenator_4
    F -> StringConcatenator_12
    <UNFILTERED> -> NullAttributeMapper_4
StringConcatenator_3
    PARM_LINE = E@Value(VGNR_4568)
    VAL_ATTR = _concatenated
    ACTION = Create New Attribute
    -> NullAttributeMapper_6
StringConcatenator_4
    PARM_LINE = Rv@Value(VGNR_4568)
    VAL_ATTR = _concatenated
    ACTION = Create New Attribute
    -> NullAttributeMapper_6
StringConcatenator_12
    PARM_LINE = Fv@Value(VGNR_4568)
    VAL_ATTR = _concatenated
    ACTION = Create New Attribute
    -> NullAttributeMapper_6
Note: Manglende vegnavn = / Vegident ("Rv25")
NullAttributeMapper_6
    ATTRCHOICE = Selected Attributes
    NEW_VALUE = @Value(_concatenated)
    ATTRLIST = vegnavn
    SOURCE_ATTR_VAL = Null Empty "Missing (Selected Attributes Only)"
    NULL_TREATMENT = New Value
    -> AttributeFilter
Note: Manglende vegnavn = / "VEG UTEN NAVN"
NullAttributeMapper_4
    ATTRCHOICE = Selected Attributes
    NEW_VALUE = Veg uten navn
    ATTRLIST = vegnavn
    SOURCE_ATTR_VAL = Null Empty "Missing (Selected Attributes Only)"
    NULL_TREATMENT = New Value
    -> AttributeCreator_13_OUTPUT_-__AttributeFilter
Note: typeveg og navn Bilferje
AttributeCreator_14
    ATTR_TABLE:
      SET_TO typeveg = Bilferje
      SET_TO vegnavn = Bilferje
    -> AttributeCreator_13_OUTPUT_-__AttributeFilter
Note: typeveg og navn Gang- og sykkelveg
AttributeCreator_13
    ATTR_TABLE:
      SET_TO typeveg = Gang- og sykkelveg
      SET_TO vegnavn = Gang- og sykkelveg
    -> AttributeCreator_13_OUTPUT_-__AttributeFilter
AttributeCreator_13_OUTPUT_-__AttributeFilter: Junction
    -> AttributeFilter

Bookmark: Trafikkretning fra Innkjøring forbudt
AttributeFilter
    ATTR_NAME = IKFB_DIRECTION
    ATTR_VALUES = 2,1,<EMPTY>,<MISSING>,<NULL>,<UNFILTERED>,<BLANK>
    2 -> AttributeCreator_16
    1 -> AttributeCreator_15
    <EMPTY> -> AttributeCreator_17
    <MISSING> -> AttributeCreator_17
    <NULL> -> AttributeCreator_17
    <UNFILTERED> -> AttributeCreator_17
    <BLANK> -> AttributeCreator_17
Note: Trafikkretning = MED
AttributeCreator_16
    ATTR_TABLE = SET_TO trafikkretning = MED
    -> EventGeometry [Events]
Note: Trafikkretning = MOT
AttributeCreator_15
    ATTR_TABLE = SET_TO trafikkretning = MOT
    -> EventGeometry [Events]
Note: Trafikkretning = BEGGE
AttributeCreator_17
    ATTR_TABLE = SET_TO trafikkretning = BEGGE
    -> EventGeometry [Events]

Bookmark: Særbehandling av fortau, trapp og sykkelveg
Note: Identifiserer envegskjørte / lenker som trolig har fortau: / VegSenterlinje på kommunal veg, og / Hpnr 0-69 eller 600-699 / + lenker som har tilknyttet objekttype fortau i NVDB
Note: Antar for enkelthets skyld at envegskjørte gater har fortau
TestFilter_7
    TEST_LIST:
      BOOL_OP,OR,COMPOSITE_TEST,<Unused>,TEST_CLAUSE,"TEST @Value(OBJTYPE) = Fortau
      TEST @Value(OBJTYPE) = Sykkelveg",CurveSegment,BOOL_OP,AND,COMPOSITE_TEST,<Unused>,TEST_CLAUSE,"TEST @Value(OBJTYPE) = VegSenterlinje
      TEST @Value(HP_4569) IN 0-69,600-699
      TEST @Value(trafikkretning) = MOT
      TEST @Value(VKTG_4566) = 5495",Fortau med,BOOL_OP,AND,COMPOSITE_TEST,<Unused>,TEST_CLAUSE,"TEST @Value(trafikkretning) = MOT
      TEST @Value(fortau) = ja
      TEST @Value(fortauside) IN 2,3",Fortau med NVDB,BOOL_OP,AND,COMPOSITE_TEST,<Unused>,TEST_CLAUSE,"TEST @Value(OBJTYPE) = VegSenterlinje
      TEST @Value(HP_4569) IN 0-69,600-699
      TEST @Value(trafikkretning) = MED
      TEST @Value(VKTG_4566) = 5495",Fortau mot,BOOL_OP,AND,COMPOSITE_TEST,<Unused>,TEST_CLAUSE,"TEST @Value(fortau) = ja
      TEST @Value(trafikkretning) = MED
      TEST @Value(fortauside) IN 1,3",Fortau mot NVDB
    DEFAULT_VALUE = Andre
    CurveSegment -> AttributeCreator_2
    Fortau med -> AttributeCreator_30
    Fortau med -> TestFilter_6
    Fortau med NVDB -> AttributeCreator_30
    Fortau mot -> AttributeCreator_19
    Fortau mot -> TestFilter_6
    Fortau mot NVDB -> AttributeCreator_19
    Andre -> TestFilter_6
Note: Overstyrer vegreferanse, og legger på typeveg og vegnavn Fortau eller Sykkelveg for lenker med objekttype Fortau eller Sykkelveg fra CurveSegment
AttributeCreator_2
    ATTR_TABLE:
      SET_TO typeveg = @Value(OBJTYPE)
      SET_TO vegnavn = @Value(OBJTYPE)
    -> StringSearcher
Note: Egne lenker for Fortau, med typeveg og navn Fortau
AttributeCreator_30
    ATTR_TABLE:
      SET_TO typeveg = Fortau
      SET_TO vegnavn = @Value(vegnavn) (fortau)
      SET_TO trafikkretning = MED
    -> TestFilter_6
AttributeCreator_19
    ATTR_TABLE:
      SET_TO typeveg = Fortau
      SET_TO vegnavn = @Value(vegnavn) (fortau)
      SET_TO trafikkretning = MOT
    -> TestFilter_6
Note: Endrer typeveg for lenker med objekttype Frittståendetrapp fra CurveSegment
TestFilter_6
    TEST_LIST = BOOL_OP,OR,COMPOSITE_TEST,<Unused>,TEST_CLAUSE,"TEST @Value(OBJTYPE) = FrittståendeTrapp",Trapp
    DEFAULT_VALUE = Andre
    Trapp -> AttributeCreator_18
    Andre -> StringSearcher
Note: typeveg Trapp
AttributeCreator_18
    ATTR_TABLE:
      SET_TO typeveg = Trapp
      SET_TO vegnavn = Trapp
    -> StringSearcher

Bookmark: Lager egne lenker for sykkelfelt
Note: Finner strekninger med sykkelfelt
StringSearcher
    REGEXP = S
    CASE = yes
    MATCHED_RESULT_ATTR = _matched_characters
    MATCHED_PARTS_ATTR = _matched_parts
    STRING_TO_SEARCH = @Value(FLTO_5528)
    MATCHED -> StringSearcher_MATCHED_-__NullAttributeMapper_2
    MATCHED -> StringSearcher_MATCHED
    NOT_MATCHED -> StringSearcher_MATCHED_-__NullAttributeMapper_2
StringSearcher_MATCHED: Junction
    -> AttributeSplitter_2
AttributeSplitter_2: Junction
    -> AttributeSplitter
Note: Liste med felt på strekningen
AttributeSplitter
    DROP_EMPTY_PARTS = No
    ATTR_NAME = FLTO_5528
    TRIM_OPTION = Both
    DELIMITER = #
    LIST_NAME = _list
    -> ListExploder
Note: Skiller ut hvert enkelt felt
ListExploder
    LIST_ATTR = _list{}
    ATTR_CONFLICT_RES = Use Incoming List
    ATTR_ACCUM_MODE = Merge Incoming List
    INDEX_ATTR = _element_index
    ELEMENTS -> StringSearcher_2
    <REJECTED> -> StringSearcher_2
Note: Finner selve sykkefeltene
StringSearcher_2
    REGEXP = S
    CASE = yes
    MATCHED_RESULT_ATTR = _matched_characters
    MATCHED_PARTS_ATTR = _matched_parts
    STRING_TO_SEARCH = @Value(_list)
    MATCHED -> AttributeCreator_29
Note: typeveg og navn Sykkelfelt
AttributeCreator_29
    ATTR_TABLE:
      SET_TO typeveg = Sykkelfelt
      SET_TO vegnavn = @Value(vegnavn) (sykkelfelt)
    -> FjernTekst
Note: Fjerner tekst i feltnummer
FjernTekst: StringReplacer
    SRC_ATTRS = _list
    FIND_TEXT = S
    REGEXP = YES
    CASE = NO
    NO_MATCH = _FME_NO_OP_
    -> TestFilter_8
Note: Splitter partallsfeltnr (mot) / og oddetallsfelnr (med)
TestFilter_8
    TEST_LIST = BOOL_OP,OR,COMPOSITE_TEST,<Unused>,TEST_CLAUSE,"TEST @Evaluate(fmod(@Value(_list),2)) = 0",Partallsfelt
    DEFAULT_VALUE = Oddetallsfelt
    Partallsfelt -> AttributeCreator_27
    Oddetallsfelt -> AttributeCreator_28
Note: Trafikkretning = MOT
AttributeCreator_27
    ATTR_TABLE = SET_TO trafikkretning = MOT
    -> AttributeCreator_28_OUTPUT_-__NullAttributeMapper_2
Note: Trafikkretning = MED
AttributeCreator_28
    ATTR_TABLE = SET_TO trafikkretning = MED
    -> AttributeCreator_28_OUTPUT_-__NullAttributeMapper_2
AttributeCreator_28_OUTPUT_-__NullAttributeMapper_2: Junction
    -> NullAttributeMapper_2
StringSearcher_MATCHED_-__NullAttributeMapper_2: Junction
    -> AnchoredSnapper_2_SNAPPED_-__NullAttributeMapper_2_Output_-__NullAttributeMapper_2

Bookmark: Fjerner OSM-lenker som dupliserer NVDB-lenker (felles noder)
GeometryExtractor
    REMOVE_GEOMETRY = No
    ATTR = _geometry
    KIND_LONG = FME Binary
    -> Matcher
Matcher
    LENIENT_MATCH = No
    SM_LIST_NAME = _match_list
    BLANK_AND_MISSING_DIFFER = No
    MATCH = NONE
    MATCHATTRS = startnode sluttnode
    MATCH_STRATEGY = Match Selected Attributes
    CNT_ATTR = _match_id
    DIFFATTRS = kilde
    SINGLE_MATCHED -> ListSearcher
    NOT_MATCHED -> AttributeManager_2
AttributeManager_2
    ATTR_TABLE:
      SET_TO invStartNode = FME_CONDITIONAL:DEFAULT_VALUE'@Value(sluttnode)'BOOL_OP;OR;COMPOSITE_TEST;<Unused>;TEST @Value(kilde) = NVDB'@Value(startnode)'FME_NUM_CONDITIONS2___
      SET_TO invSluttNode = FME_CONDITIONAL:DEFAULT_VALUE'@Value(startnode)'BOOL_OP;OR;COMPOSITE_TEST;<Unused>;TEST @Value(kilde) = NVDB'@Value(sluttnode)'FME_NUM_CONDITIONS2___
    -> Matcher_2
Matcher_2
    LENIENT_MATCH = No
    SM_LIST_NAME = _match_list
    BLANK_AND_MISSING_DIFFER = No
    MATCH = NONE
    MATCHATTRS = invStartNode invSluttNode
    MATCH_STRATEGY = Match Selected Attributes
    CNT_ATTR = _match_id
    DIFFATTRS = kilde
    SINGLE_MATCHED -> ListSearcher
    NOT_MATCHED -> NullAttributeMapper
ListSearcher
    LIST_ATTR = _match_list{}.kilde
    ATTR_VALUE = NVDB
    SEARCH_TYPE = First exact match
    INDEX_ATTR = _list_index
    FOUND -> ListIndexer
ListIndexer
    LIST_ATTR = _match_list{}
    INDEX = @Value(_list_index)
    -> GeometryReplacer
GeometryReplacer
    KIND_LONG = FME Binary
    SOURCE = @Value(_geometry)
    REMOVE_ATTRIBUTE = Yes
    -> NullAttributeMapper

FME custom transformer EventGeometry

Parameters:
- _rlRouteID =   # Network RouteID attribute
- _rlFrom =   # Network From measure attribute
- _rlTo =   # Network To measure attribute
- _eventRouteID =   # Event Route ID attribute
- _eventFrom =   # Event From Measure attribute
- _eventTo =   # Event To measure attribute
- _measureMode = 3D   # Measurement Mode
- _dimension = 3   # Length Dimension

Network (input)
    -> AttributeCreator
AttributeCreator
    ATTR_LIST = _routeID,$(_rlRouteID),_rlFrom,$(_rlFrom),_rlTo,$(_rlTo)
    -> InlineQuerier [ROADLINKS]
Events (input)
    -> Counter
Counter
    SCOPE = Global
    START = 0
    DOMAIN = counter
    CNT_ATTR = _eventID
    -> AttributeCreator_2
AttributeCreator_2
    ATTR_LIST = _routeID,$(_eventRouteID),_eventFrom,$(_eventFrom),_eventTo,$(_eventTo)
    -> InlineQuerier [EVENTS]
Note: Select road segements within / the measure of the events
InlineQuerier
    QUERY_DEF:
      SEGMENTS,SELECT * FROM ROADLINKS
      INNER JOIN EVENTS ON ROADLINKS._routeID = EVENTS._routeID
      WHERE (ROADLINKS._rlFrom < EVENTS._eventTo AND ROADLINKS._rlTo > EVENTS._eventFrom)
      OR (ROADLINKS._rlFrom = EVENTS._eventFrom AND EVENTS._eventFrom = EVENTS._eventTo)
      OR (ROADLINKS._rlTo = EVENTS._eventTo AND EVENTS._eventFrom = EVENTS._eventTo),FIRST
    QUERY_SCHEMA = SEGMENTS,_routeID,varchar(38),_rlFrom,float,_rlTo,float,ROADLINKS.fme_feature_content,fme_feature_content,_eventID,varchar(38),_eventFrom,float,_eventTo,float,EVENTS.fme_feature_content,fme_feature_content
    TABLE_DEF = ROADLINKS,_routeID,varchar(38),_rlFrom,float,_rlTo,float,EVENTS,_eventID,varchar(38),_routeID,varchar(38),_eventFrom,float,_eventTo,float
    SEGMENTS -> LengthCalculator
Note: Calculate segment length
LengthCalculator
    DIM = $(_dimension)
    MULT = 1
    LEN_ATTR = _length
    -> ExpressionEvaluator
Note: Calculate scale
ExpressionEvaluator
    EXPRESSION = @Value(_length)/((@Value(_rlTo)-@Value(_rlFrom))+0.000)
    VAL_ATTR = _scale
    -> StringFormatter
Note: Avrunder til 8 desimaler for å unngå / problem med eksponentialverdier
StringFormatter
    SRC_ATTRS = _eventFrom,_eventTo
    FORMAT = .8f
    -> TestFilter_3
Note: Filter on what part of / the segment to be snipped
TestFilter_3
    TEST_LIST:
      BOOL_OP,OR,COMPOSITE_TEST,<Unused>,TEST_CLAUSE,"TEST ""@Value(_eventFrom)"" = ""@Value(_eventTo)""",Point events,BOOL_OP,AND,COMPOSITE_TEST,<Unused>,TEST_CLAUSE,"TEST ""@Value(_rlFrom)"" < ""@Value(_eventFrom)""
      TEST ""@Value(_rlTo)"" > ""@Value(_eventTo)""",Within segment,BOOL_OP,AND,COMPOSITE_TEST,<Unused>,TEST_CLAUSE,"TEST ""@Value(_rlFrom)"" >= ""@Value(_eventFrom)""
      TEST ""@Value(_rlTo)"" > ""@Value(_eventTo)""",Start of segment,BOOL_OP,AND,COMPOSITE_TEST,<Unused>,TEST_CLAUSE,"TEST ""@Value(_rlFrom)"" < ""@Value(_eventFrom)""
      TEST ""@Value(_rlTo)"" <= ""@Value(_eventTo)""",End of segment,BOOL_OP,AND,COMPOSITE_TEST,<Unused>,TEST_CLAUSE,"TEST ""@Value(_rlFrom)"" >= ""@Value(_eventFrom)""
      TEST ""@Value(_rlTo)"" <= ""@Value(_eventTo)""",Complete segment
    DEFAULT_VALUE = <UNFILTERED>
    Point events -> ExpressionEvaluator_2
    Within segment -> ExpressionEvaluator_3
    Start of segment -> ExpressionEvaluator_6
    End of segment -> ExpressionEvaluator_5
    Complete segment -> AttributeRemover
AttributeRemover
    REMOVE_ATTRS = _rlFrom,_rlTo,_scale,_snip,_x,_y,_z,_snipFrom,_snipTo
    -> GeometryFilter
GeometryFilter
    BREAK_AGG = No
    POINT -> Points (output)
    LINE -> Lines (output)
Points (output)
Lines (output)

Bookmark: Point events
Note: Calculate position
ExpressionEvaluator_2
    EXPRESSION = (@Value(_eventFrom)-@Value(_rlFrom))*@Value(_scale)
    VAL_ATTR = _snip
    -> Snipper
Note: Snip start of segment
Snipper
    SNIPMODE = Distance (Value)
    STARTLOCATIONATTR = @Value(_snip)
    ENDLOCATIONATTR = -1
    MEASUREMENTTYPE = $(_measureMode)
    -> CoordinateExtractor
Note: Get start coordinates
CoordinateExtractor
    Z_ATTR = _z
    Y_ATTR = _y
    Z_DEFAULT = -9999
    IND = 0
    X_ATTR = _x
    -> 3DPointReplacer
Note: Replace geometry with point coordinates
3DPointReplacer
    XVALATTR = @Value(_x)
    YVALATTR = @Value(_y)
    ZVALATTR = @Value(_z)
    POINT -> AttributeRemover

Bookmark: Events that are within a segment
Note: Calculate snip from
ExpressionEvaluator_3
    EXPRESSION = (@Value(_eventFrom)-@Value(_rlFrom))*@Value(_scale)
    VAL_ATTR = _snipFrom
    -> ExpressionEvaluator_4
Note: Calculate snip to
ExpressionEvaluator_4
    EXPRESSION = (@Value(_eventTo)-@Value(_rlFrom))*@Value(_scale)
    VAL_ATTR = _snipTo
    -> Snipper_2
Note: Snip segment
Snipper_2
    SNIPMODE = Distance (Value)
    STARTLOCATIONATTR = @Value(_snipFrom)
    ENDLOCATIONATTR = @Value(_snipTo)
    MEASUREMENTTYPE = $(_measureMode)
    -> AttributeRemover

Bookmark: Events that are on the start of a segment
Note: Calculate snip to
ExpressionEvaluator_6
    EXPRESSION = (@Value(_eventTo)-@Value(_rlFrom))*@Value(_scale)
    VAL_ATTR = _snipTo
    -> Snipper_3
Note: Snip segment
Snipper_3
    SNIPMODE = Distance (Value)
    STARTLOCATIONATTR = 0
    ENDLOCATIONATTR = @Value(_snipTo)
    MEASUREMENTTYPE = $(_measureMode)
    -> AttributeRemover

Bookmark: Events that are on the end of a segment
Note: Calculate snip from
ExpressionEvaluator_5
    EXPRESSION = (@Value(_eventFrom)-@Value(_rlFrom))*@Value(_scale)
    VAL_ATTR = _snipFrom
    -> Snipper_4
Note: Snip segment
Snipper_4
    SNIPMODE = Distance (Value)
    STARTLOCATIONATTR = @Value(_snipFrom)
    ENDLOCATIONATTR = -1
    MEASUREMENTTYPE = $(_measureMode)
    -> AttributeRemover

FME custom transformer UniqeSegments

BREAKPOINTLIST (input)
    -> AttributeExposer_3
AttributeExposer_3
    ATTR_LIST = _idx,_maxIdx,RoadLinkID,_Bp_list{}.BREAKPOINT,_Bp_list{}.RoadLinkID,_Bp_list{}.fme_feature_type,_Bp_list{}.fme_basename,_Bp_list{}.fme_dataset
    -> ListIndexer

Bookmark: From value
ListIndexer
    LIST_ATTR = _Bp_list{}
    INDEX = @Value(_idx)
    -> AttributeExposer
AttributeExposer
    ATTR_LIST = BREAKPOINT
    -> AttributeManager
AttributeManager
    ATTR_TABLE:
      RENAME_SET_VALUE BREAKPOINT > FromVal
      SET_TO _next = @Evaluate(@Value(_idx)+1)
    -> ListIndexer_2

Bookmark: To value
ListIndexer_2
    LIST_ATTR = _Bp_list{}
    INDEX = @Value(_next)
    -> AttributeExposer_2
AttributeExposer_2
    ATTR_LIST = BREAKPOINT
    -> AttributeManager_2
AttributeManager_2
    ATTR_TABLE:
      RENAME_SET_VALUE BREAKPOINT > ToVal
      SET_TO _next = @Evaluate(@Value(_idx)+1)
    -> AttributeManager_3
    -> TestFilter

Bookmark: Finished segements
AttributeManager_3
    ATTR_TABLE:
      REMOVE _idx
      REMOVE _maxIdx
      REMOVE _next
      REMOVE _Bp_list{}.BREAKPOINT
      REMOVE _Bp_list{}.RoadLinkID
      REMOVE _Bp_list{}.fme_feature_type
      REMOVE _Bp_list{}.fme_basename
      REMOVE _Bp_list{}.fme_dataset
    -> Unique_Segments (output)
Unique_Segments (output)

Bookmark: Test for more segments
TestFilter
    TEST_LIST = BOOL_OP,OR,COMPOSITE_TEST,<Unused>,TEST_CLAUSE,"TEST @Value(_next) = @Value(_maxIdx)",Last
    DEFAULT_VALUE = <UNFILTERED>
    <UNFILTERED> -> AttributeCreator
AttributeCreator
    ATTR_TABLE = SET_TO _idx = @Value(_next)
    -> BREAKPOINTLIST (output)
BREAKPOINTLIST (output)

FME custom transformer EventOverlayer

Parameters:
- RoadLinkID =   # " " RoadLinkID
- FromVal =   # " " FromVal
- ToVal =   # " " ToVal

Event_table_A (input)
    -> AttributeCreator_2
AttributeCreator_2
    ATTR_TABLE:
      SET_TO RoadLinkID = $(RoadLinkID)
      SET_TO FromVal = $(FromVal)
      SET_TO ToVal = $(ToVal)
    -> GeometryRemover
GeometryRemover
    -> SegmentizeTable [Events]
    -> Segments [Event_Tables]
Event_table_B (input)
    -> AttributeCreator_3
AttributeCreator_3
    ATTR_TABLE:
      SET_TO RoadLinkID = $(RoadLinkID)
      SET_TO FromVal = $(FromVal)
      SET_TO ToVal = $(ToVal)
    -> GeometryRemover_2
GeometryRemover_2
    -> Segments [Event_Tables]
    -> SegmentizeTable_2 [Events]
Note: Common segments
Segments
    RoadLinkID = @Value(RoadLinkID)
    FromVal = @Value(FromVal)
    __COMPOUND_PARAMETERS = -
    ToVal = @Value(ToVal)
    Unique_Segment_List -> SegmentizeTable [SegmentList]
    Unique_Segment_List -> SegmentizeTable_2 [SegmentList]
Note: Segmentize table A
SegmentizeTable
    eventRoadLink = @Value(RoadLinkID)
    __COMPOUND_PARAMETERS = -
    eventFromVal = @Value(FromVal)
    eventToVal = @Value(ToVal)
    Segmented -> FeatureMerger [REQUESTOR]
Note: Segmentize table B
SegmentizeTable_2
    eventRoadLink = @Value(RoadLinkID)
    __COMPOUND_PARAMETERS = -
    eventFromVal = @Value(FromVal)
    eventToVal = @Value(ToVal)
    Segmented -> FeatureMerger [SUPPLIER]
Note: Merge segments
FeatureMerger
    JOIN_KEYS = @Value(_SegId) @Value(_SegId) AUTO
    ATTR_CONFLICT_RES = Use Requestor
    PROCESS_DUPS = No
    MERGE_TYPE = Attributes Only
    ATTR_ACCUM_MODE = Merge Supplier
    SUPPLIERS_FIRST = No
    IGNORE_NULLS = No
    REJECT_NULL_MISSING_KEYS = No
    MERGED -> Common_Segments (output)
    NOT_MERGED -> Only_A (output)
    UNREFERENCED -> Only_B (output)
Common_Segments (output)
Only_A (output)
Only_B (output)

FME custom transformer NodeElevation

2D_Lines (input)
    -> AttributeRemover
AttributeRemover
    REMOVE_ATTRS = _endZ,_startZ
    -> Counter
Counter
    SCOPE = Global
    START = 0
    DOMAIN = counter
    CNT_ATTR = _LinkID
    -> VertexCreator
    -> VertexCreator_2
    -> FeatureMerger [REQUESTOR]
3D_Lines (input)
    -> VertexCreator_3
    -> VertexCreator_4

Bookmark: Vertices on lines without elevation
Note: Start vertices
VertexCreator
    MODE_NAME = Replace with Point
    YVAL = @Value(_startY)
    XVAL = @Value(_startX)
    -> AttributeCreator
AttributeCreator
    ATTR_TABLE = SET_TO _position = START
    -> AttributeKeeper_2
Note: End vertices
VertexCreator_2
    MODE_NAME = Replace with Point
    YVAL = @Value(_endY)
    XVAL = @Value(_endX)
    -> AttributeCreator_2
AttributeCreator_2
    ATTR_TABLE = SET_TO _position = END
    -> AttributeKeeper_2
AttributeKeeper_2
    KEEP_ATTRS = _LinkID,_position
    -> Bufferer

Bookmark: Overlay: Get elevation from nearby vertices with elevation
Note: 1m buffer
Bufferer
    CAP_STYLE = Round
    OFFSET = 1
    INTERP_SEGMENTS = 8
    BUFFERED -> SpatialRelator [Requestor]
Note: Find 3D vertices within buffer of 2D vertices
SpatialRelator
    ATTR_CONFLICT_RES = Use Requestor
    LIST_NAME = _relationships
    CALC_CARD = Yes
    AGGREGATE_HANDLING = Yes
    ATTR_ACCUM_MODE = Merge Supplier
    CURVE_BOUNDARY_RULE_PARAM = Default Rule
    SUCCESS_ATTR = _related_candidates
    PREDICATES = INTERSECTS
    -> AttributeRemover_2
    <Rejected> -> AttributeRemover_2
AttributeRemover_2
    LIST_ATTRS = _relationships{}
    -> AttributeFilter_2

Bookmark: Vertices on lines with elevation
Note: Start vertices
VertexCreator_3
    MODE_NAME = Replace with Point
    ZVAL = @Value(_startZ)
    YVAL = @Value(_startY)
    XVAL = @Value(_startX)
    -> AttributeRenamer
AttributeRenamer
    ATTR_TABLE = RENAME_SET_DEFAULT _startZ > _Z
    -> AttributeKeeper
Note: End vertices
VertexCreator_4
    MODE_NAME = Replace with Point
    ZVAL = @Value(_endZ)
    YVAL = @Value(_endY)
    XVAL = @Value(_endX)
    -> AttributeRenamer_2
AttributeRenamer_2
    ATTR_TABLE = RENAME_SET_DEFAULT _endZ > _Z
    -> AttributeKeeper
AttributeKeeper
    KEEP_ATTRS = _Z
    -> SpatialRelator [Supplier]

Bookmark: Merge information from start and end vertices
AttributeFilter_2
    ATTR_NAME = _position
    ATTR_VALUES = <EMPTY>,<MISSING>,<NULL>,<BLANK>,<UNFILTERED>,START,END
    START -> AttributeRenamer_3
    END -> AttributeRenamer_4
AttributeRenamer_3
    ATTR_TABLE = RENAME_SET_DEFAULT _Z > _StartNodeZ
    -> FeatureMerger_2 [REQUESTOR]
AttributeRenamer_4
    ATTR_TABLE = RENAME_SET_DEFAULT _Z > _EndNodeZ
    -> FeatureMerger_2 [SUPPLIER]
Note: Combine start and end vertices
FeatureMerger_2
    JOIN_KEYS = @Value(_LinkID) @Value(_LinkID) AUTO
    ATTR_CONFLICT_RES = Use Requestor
    PROCESS_DUPS = No
    MERGE_TYPE = Attributes Only
    ATTR_ACCUM_MODE = Merge Supplier
    SUPPLIERS_FIRST = No
    IGNORE_NULLS = No
    REJECT_NULL_MISSING_KEYS = No
    MERGED -> FeatureMerger [SUPPLIER]
    NOT_MERGED -> FeatureMerger [SUPPLIER]
    UNREFERENCED -> FeatureMerger [SUPPLIER]

Bookmark: Identify lines with elevation on both vertices
Note: Connect evaluation values to the line
FeatureMerger
    JOIN_KEYS = @Value(_LinkID) @Value(_LinkID) AUTO
    ATTR_CONFLICT_RES = Use Requestor
    PROCESS_DUPS = No
    MERGE_TYPE = Attributes Only
    ATTR_ACCUM_MODE = Merge Supplier
    SUPPLIERS_FIRST = No
    IGNORE_NULLS = No
    REJECT_NULL_MISSING_KEYS = No
    MERGED -> NullAttributeMapper_2
NullAttributeMapper_2
    ATTRCHOICE = Selected Attributes
    NEW_VALUE = NULL
    ATTRLIST = _EndNodeZ _StartNodeZ
    SOURCE_ATTR_VAL = Null Empty "Missing (Selected Attributes Only)"
    NULL_TREATMENT = New Value
    -> TestFilter
TestFilter
    TEST_LIST:
      TEST_CLAUSE,"TEST @Value(_StartNodeZ) != NULL
      TEST @Value(_EndNodeZ) != NULL",TEST_LIST,"&_StartNodeZ,!=,NULL,&_EndNodeZ,!=,NULL",TEST_MODE,Automatic,BOOL_OP,AND,Both_ends,TEST_CLAUSE,"TEST @Value(_StartNodeZ) != NULL
      TEST @Value(_EndNodeZ) = NULL",TEST_LIST,"&_StartNodeZ,!=,NULL,&_EndNodeZ,=,NULL",TEST_MODE,Automatic,BOOL_OP,AND,Start_only,TEST_CLAUSE,"TEST @Value(_StartNodeZ) = NULL
      TEST @Value(_EndNodeZ) != NULL",TEST_LIST,"&_StartNodeZ,=,NULL,&_EndNodeZ,!=,NULL",TEST_MODE,Automatic,BOOL_OP,AND,End_only
    DEFAULT_VALUE = <UNFILTERED>
    Both_ends -> 3DInterpolator
    Start_only -> 2D_Lines (output)
    End_only -> 2D_Lines (output)
    <UNFILTERED> -> 2D_Lines (output)
Note: Interpolate elevation for lines with / elevation for both start and end vertices
3DInterpolator
    ZSTARTATTR = @Value(_StartNodeZ)
    ZENDATTR = @Value(_EndNodeZ)
    -> InterpolatedTo3D (output)
InterpolatedTo3D (output)
2D_Lines (output)

FME custom transformer LineVertexElevationCorrector
Fixes missing and bad elevation values for line vertexes. Bad elevation is when the elevation is bellow a given limit value.
Lines with only missing or bad values are set to constant elevation = 0. 
For lines that have some good values and some bad or missing, the bad elevations are replaced with the average value of the two closest vertexes with elevation.
Created by: Knut Jetlund
Version date: 09.11.2007

Parameters:
- NullLimit =   # Null value limit

Input_lines (input)
    -> AttributeCreator_2
Note: ObjID
ObjID: Counter
    SCOPE = Global
    START = 0
    DOMAIN = counter
    CNT_ATTR = ObjID
    -> BoundsExtractor
Note: Extract bounds
BoundsExtractor
    ZMAX = _zmax
    YMIN = _ymin
    XMIN = _xmin
    XMAX = _xmax
    ZMIN = _zmin
    YMAX = _ymax
    -> TestFilter
Note: Connect original lines to the new objects
FeatureMerger_3
    JOIN_KEYS = @Value(ObjID) @Value(ObjID) AUTO
    ATTR_CONFLICT_RES = Use Requestor
    PROCESS_DUPS = No
    MERGE_TYPE = Attributes Only
    ATTR_ACCUM_MODE = Merge Supplier
    SUPPLIERS_FIRST = No
    IGNORE_NULLS = No
    REJECT_NULL_MISSING_KEYS = No
    MERGED -> GeometryReplacer
    NOT_MERGED -> AttributeRemover_2
Note: Replace geometry
GeometryReplacer
    KIND_LONG = FME Binary
    SOURCE = @Value(FME_geometry)
    REMOVE_ATTRIBUTE = Yes
    -> AttributeRemover_2
Note: Remove internal attributes
AttributeRemover_2
    REMOVE_ATTRS = _zmin,DefNullValue,ObjID,_ymin,_zmax,_xmin,NullLimit,_ymax,_xmax
    -> Lines_with_elevation (output)
Lines_with_elevation (output)

Bookmark: Define parameters
AttributeCreator_2
    ATTR_TABLE:
      SET_TO NullLimit = $(NullLimit)
      SET_TO DefNullValue = $(NullLimit)-100
    -> ObjID

Bookmark: Force lines with no elevation to be 2D
Note: Lines with all elevation / values bellow test limit
TestFilter
    TEST_LIST = BOOL_OP,OR,COMPOSITE_TEST,<Unused>,TEST_CLAUSE,"TEST @Value(_zmax) <= $(NullLimit)",NoElevation
    DEFAULT_VALUE = HasElevation
    NoElevation -> 2DForcer
    HasElevation -> FeatureMerger_3 [REQUESTOR]
    HasElevation -> TestFilter_2
2DForcer
    2D -> AttributeRemover_3
Note: Remove internal attributes
AttributeRemover_3
    REMOVE_ATTRS = DefNullValue,NullLimit,ObjID
    -> NoElevation (output)
NoElevation (output)

Bookmark: Find lines with some missing elevations
Note: Lines with some / "bad" vertices
TestFilter_2
    TEST_LIST = BOOL_OP,OR,COMPOSITE_TEST,<Unused>,TEST_CLAUSE,"TEST @Value(_zmin) <= $(NullLimit)",SomeBellow
    DEFAULT_VALUE = <UNFILTERED>
    SomeBellow -> AttributeKeeper
Note: Split points with and / without elevation
TestFilter_3
    TEST_LIST = BOOL_OP,OR,COMPOSITE_TEST,<Unused>,TEST_CLAUSE,"TEST @Value(Z) <= $(NullLimit)",NoElevation
    DEFAULT_VALUE = HasElevation
    NoElevation -> AttributeManager
    HasElevation -> AttributeKeeper_5
AttributeKeeper_5
    KEEP_ATTRS = VertexID,ObjID,_zmax,Z
    -> NeighborFinder [CANDIDATE]
    -> Sorter

Bookmark: Extract points and coordinates
AttributeKeeper
    KEEP_ATTRS = ObjID,NullLimit,DefNullValue,_zmax
    -> Chopper
Note: Extract line vertices
Chopper
    CHOPPED_ATTR = _chopped
    REMNANT_ATTR = _remnant
    MAX_VERTICES = 1
    MODE = By Vertex
    -> VertexID
Note: VertexID
VertexID: Counter
    SCOPE = Global
    START = 0
    DOMAIN = counter
    CNT_ATTR = VertexID
    -> CoordinateFetcher
Note: Extract coordinates
CoordinateFetcher: CoordinateExtractor
    Z_ATTR = Z
    Y_ATTR = N
    Z_DEFAULT = -9999
    IND = 0
    MODE = Specify Coordinate
    X_ATTR = E
    -> NullAttributeMapper
Note: Set null values to / default elevation
NullAttributeMapper
    ATTRCHOICE = Selected Attributes
    NEW_VALUE = @Value(DefNullValue)
    ATTRLIST = Z
    SOURCE_ATTR_VAL = Null
    NULL_TREATMENT = New Value
    -> GeometryExtractor_2
Note: Save geometry
GeometryExtractor_2
    REMOVE_GEOMETRY = No
    ATTR = Pnt_geometry
    KIND_LONG = FME Binary
    -> TestFilter_3

Bookmark: Find elevation from neighbor points
AttributeManager
    ATTR_TABLE:
      REMOVE NullLimit
      REMOVE DefNullValue
      REMOVE _chopped
      REMOVE _remnant
      RENAME_SET_VALUE VertexID > OrgVertexID
      REMOVE Z
    -> NeighborFinder [BASE]
Note: Find neighbor vertices / with elevation, within 100m
NeighborFinder
    TREAT_POLYGON_AS = Lines
    INSERT_VERTEX = No
    CANDIDATES_FIRST = No
    ATTR_CONFLICT_RES = Use Base
    MAX = 100
    MODE = Bases and Candidates
    ATTR_ACCUM_MODE = Merge Candidate
    GROUP_BY = ObjID
    CLOSE_LIST_NAME = Cand_list
    MATCHED -> ListExploder
    UNMATCHED_BASE -> 3DForcer_2
Note: XPlode neighbor list
ListExploder
    LIST_ATTR = Cand_list{}
    ATTR_CONFLICT_RES = Use Incoming List
    ATTR_ACCUM_MODE = Merge Incoming List
    INDEX_ATTR = _element_index
    ELEMENTS -> TestFilter_4
Note: Differ between neighbor / vertices before and after / this vertex in the line
TestFilter_4
    TEST_LIST = BOOL_OP,OR,COMPOSITE_TEST,<Unused>,TEST_CLAUSE,"TEST @Value(VertexID) < @Value(OrgVertexID)",Before
    DEFAULT_VALUE = After
    Before -> BeforeList
    After -> AfterList
Note: Create list of neighbors before
BeforeList: ListBuilder
    GRP_BY = E N ObjID OrgVertexID Pnt_geometry
    LIST_NAME = Before_List
    -> ListSorter
Note: Sort by distance
ListSorter
    SRC_LIST = Before_List{}.distance
    ORDER = Ascending
    TYPE = Numeric
    -> ListIndexer
Note: Exctract closest vertix
ListIndexer
    LIST_ATTR = Before_List{}
    INDEX = 0
    -> AttributeManager_3
AttributeManager_3
    ATTR_TABLE:
      RENAME_SET_VALUE OrgVertexID > VertexID
      REMOVE _zmax
      RENAME_SET_VALUE Z > Before_Z
      REMOVE _distance
      REMOVE _angle
      REMOVE _candidate_angle
      REMOVE _candidate_label_angle
      REMOVE _closest_candidate_x
      REMOVE _closest_candidate_y
      REMOVE _closest_base_x
      REMOVE _closest_base_y
      REMOVE distance
      REMOVE angle
      REMOVE candidate_angle
      REMOVE candidate_label_angle
      REMOVE closest_candidate_x
      REMOVE closest_candidate_y
      REMOVE closest_base_x
      REMOVE closest_base_y
      REMOVE _element_index
      REMOVE Before_List{}.ObjID
      REMOVE Before_List{}._zmax
      REMOVE Before_List{}.OrgVertexID
      REMOVE Before_List{}.E
      REMOVE Before_List{}.N
      REMOVE Before_List{}.Pnt_geometry
      REMOVE Before_List{}.VertexID
      REMOVE Before_List{}.Z
      REMOVE Before_List{}._distance
      REMOVE Before_List{}._angle
      REMOVE Before_List{}._candidate_angle
      REMOVE Before_List{}._candidate_label_angle
      REMOVE Before_List{}._closest_candidate_x
      REMOVE Before_List{}._closest_candidate_y
      REMOVE Before_List{}._closest_base_x
      REMOVE Before_List{}._closest_base_y
      REMOVE Before_List{}.distance
      REMOVE Before_List{}.angle
      REMOVE Before_List{}.candidate_angle
      REMOVE Before_List{}.candidate_label_angle
      REMOVE Before_List{}.closest_candidate_x
      REMOVE Before_List{}.closest_candidate_y
      REMOVE Before_List{}.closest_base_x
      REMOVE Before_List{}.closest_base_y
      REMOVE Before_List{}._element_index
    -> FeatureMerger_2 [REQUESTOR]
Note: Create list of neighbors after
AfterList: ListBuilder
    GRP_BY = E N ObjID OrgVertexID Pnt_geometry
    LIST_NAME = After_List
    -> ListSorter_2
Note: Sort by distance
ListSorter_2
    SRC_LIST = After_List{}.distance
    ORDER = Ascending
    TYPE = Numeric
    -> ListIndexer_2
Note: Exctract closest vertix
ListIndexer_2
    LIST_ATTR = After_List{}
    INDEX = 0
    -> AttributeManager_2
AttributeManager_2
    ATTR_TABLE:
      RENAME_SET_VALUE OrgVertexID > VertexID
      REMOVE After_List{}.ObjID
      REMOVE After_List{}._zmax
      REMOVE After_List{}.OrgVertexID
      REMOVE After_List{}.E
      REMOVE After_List{}.N
      REMOVE After_List{}.Pnt_geometry
      REMOVE After_List{}.VertexID
      REMOVE After_List{}.Z
      REMOVE After_List{}._distance
      REMOVE After_List{}._angle
      REMOVE After_List{}._candidate_angle
      REMOVE After_List{}._candidate_label_angle
      REMOVE After_List{}._closest_candidate_x
      REMOVE After_List{}._closest_candidate_y
      REMOVE After_List{}._closest_base_x
      REMOVE After_List{}._closest_base_y
      REMOVE After_List{}.distance
      REMOVE After_List{}.angle
      REMOVE After_List{}.candidate_angle
      REMOVE After_List{}.candidate_label_angle
      REMOVE After_List{}.closest_candidate_x
      REMOVE After_List{}.closest_candidate_y
      REMOVE After_List{}.closest_base_x
      REMOVE After_List{}.closest_base_y
      REMOVE After_List{}._element_index
      REMOVE _zmax
      RENAME_SET_VALUE Z > After_Z
      REMOVE _distance
      REMOVE _angle
      REMOVE _candidate_angle
      REMOVE _candidate_label_angle
      REMOVE _closest_candidate_x
      REMOVE _closest_candidate_y
      REMOVE _closest_base_x
      REMOVE _closest_base_y
      REMOVE distance
      REMOVE angle
      REMOVE candidate_angle
      REMOVE candidate_label_angle
      REMOVE closest_candidate_x
      REMOVE closest_candidate_y
      REMOVE closest_base_x
      REMOVE closest_base_y
      REMOVE _element_index
    -> FeatureMerger_2 [SUPPLIER]
Note: Combine Z-values from closest / point before and after
FeatureMerger_2
    JOIN_KEYS = @Value(VertexID) @Value(VertexID) AUTO
    ATTR_CONFLICT_RES = Use Requestor
    PROCESS_DUPS = No
    MERGE_TYPE = Attributes Only
    ATTR_ACCUM_MODE = Merge Supplier
    SUPPLIERS_FIRST = No
    IGNORE_NULLS = No
    REJECT_NULL_MISSING_KEYS = No
    MERGED -> AttributeManager_5
    NOT_MERGED -> AttributeCopier
    UNREFERENCED -> AttributeCopier_2
Note: Calculate average Z
AttributeManager_5
    ATTR_TABLE = SET_TO Z = @Evaluate((@Value(After_Z)+@Value(Before_Z))/2.000)
    -> VertexCreator
Note: No vertex after, set Z = Before_Z
AttributeCopier
    ATTR_TABLE = COPY Before_Z > Z
    -> VertexCreator
Note: No vertex before, set Z = After_Z
AttributeCopier_2
    ATTR_TABLE = COPY After_Z > Z
    -> VertexCreator
VertexCreator
    MODE_NAME = Replace with Point
    ZVAL = @Value(Z)
    YVAL = @Value(N)
    XVAL = @Value(E)
    -> Sorter
Note: No neighbor vertex found. / Set elevation = max elevation / for the line
3DForcer_2
    KEEPZVAL = No
    ZVALATTR = @Value(_zmax)
    -> AttributeRenamer_4
AttributeRenamer_4
    ATTR_TABLE = RENAME_SET_DEFAULT OrgVertexID > VertexID
    -> Sorter

Bookmark: Reconstruct lines
Note: Sorter
Sorter
    SORT_PARM = ObjID NUMERIC ASCENDING VertexID NUMERIC ASCENDING
    SORTED -> PointConnector
Note: Reconstruct lines
PointConnector
    BREAKATTR = ObjID
    ACCUM_INPUT_ATTRS = Get Attributes From One Representative Feature
    LINE -> AttributeManager_4
    POLYGON -> GeometryPartExtractor
GeometryPartExtractor
    GQUERY:
      for $geom in //geometry
      where $geom/@fme_geometry_type = 'IFMELine'
      return number($geom/@fme_id)
    EXTRACTTYPE_PARAM = Extract
    PROCESSED -> AttributeManager_4
AttributeManager_4
    ATTR_TABLE:
      REMOVE E
      REMOVE N
      REMOVE Pnt_geometry
      REMOVE VertexID
      REMOVE Before_Z
      REMOVE After_Z
      REMOVE Z
      REMOVE _zmax
    -> GeometryExtractor
Note: Extract geometry to attribute
GeometryExtractor
    REMOVE_GEOMETRY = No
    ATTR = FME_geometry
    KIND_LONG = FME Binary
    -> FeatureMerger_3 [SUPPLIER]

FME custom transformer Topologirydding

Parameters:
- dXYlim = 1   # Grenseverdi for korte lenker

Noder (input)
    -> ListElementCounter
Lenker (input)
    -> FeatureMerger [REQUESTOR]
Note: Finner tilhørende lenke, dvs lenker der minst en ende er blindveg
FeatureMerger
    JOIN_KEYS = @Value(_edge_id) @Value(_node_arc_id) AUTO
    ATTR_CONFLICT_RES = Use Requestor
    LIST_NAME = _nodeListe
    PROCESS_DUPS = No
    MERGE_TYPE = Attributes Only
    ATTR_ACCUM_MODE = Merge Supplier
    GROUP_BY = medium
    SUPPLIERS_FIRST = No
    IGNORE_NULLS = No
    REJECT_NULL_MISSING_KEYS = No
    MERGED -> SpatialRelator [Requestor]
    NOT_MERGED -> AttributeKeeper_2
    NOT_MERGED -> NULL
Frinavigeringssoner (input)
    -> SpatialRelator [Supplier]
Note: Finner blindlenker som berører frinavigeringssoner. Disse skal bevares
SpatialRelator
    LIST_NAME = _relationships
    CALC_CARD = No
    AGGREGATE_HANDLING = Yes
    CURVE_BOUNDARY_RULE_PARAM = Default Rule
    SUCCESS_ATTR = _related_candidates
    PREDICATES = INTERSECTS
    -> TestFilter
TestFilter
    TEST_LIST = BOOL_OP,OR,COMPOSITE_TEST,<Unused>,TEST_CLAUSE,"TEST @Value(_related_candidates) = 0",None
    DEFAULT_VALUE = Intersects
    None -> Snapper_2
    Intersects -> AttributeKeeper_2
    Intersects -> NULL
Note: Snapper sammen / møtende blindlenker
Snapper_2
    SNAPTYPE_PARAM = Segment Snapping
    TOLERANCE = $(dXYlim)
    GROUP_BY = medium
    SNAPPED -> Counter
    UNTOUCHED -> Counter
Counter
    SCOPE = Global
    START = 0
    DOMAIN = counter
    CNT_ATTR = _BlindID
    -> AttributeKeeper_2
    -> GeometryExtractor
GeometryExtractor
    OGCVERSION = 1.1
    KIND_LONG = FME Binary
    ATTR = _geometry
    -> ListExploder_2
    -> AttributeRemover_4
AttributeRemover_4
    LIST_ATTRS = _nodeListe{}
    -> FeatureMerger_2 [REQUESTOR]
Note: Alle (begge) blindnoder / på hver lenke
ListExploder_2
    LIST_ATTR = _nodeListe{}
    ATTR_CONFLICT_RES = Use Incoming List
    ATTR_ACCUM_MODE = Merge Incoming List
    INDEX_ATTR = _element_index
    ELEMENTS -> TestFilter_2
Note: Samler alle lenker som skal være kilde for potensiell ny posisjon på blindender
AttributeKeeper_2
    KEEP_ATTRS = medium
    -> NeighborFinder_2 [CANDIDATE]
AttributeKeeper_4
    KEEP_ATTRS = medium
    -> PointOnLineOverlayer [POINT]
Note: Samler alle lenker som skal være uendret
NULL
    -> AttributeRemover_3
AttributeRemover_3
    REMOVE_ATTRS = _BlindID,_arc_id,_concatenated,_from_node,_geometry,_left_edge,_left_polygon,_length,_list_index,_node_arc_id,_node_number,_overlaps,_polygons,_right_edge,_right_polygon,_to_node,_xmax,_xmin,_ymax,_ymin,_zmax,_zmin,fme_arc_id
    -> ListRemover_2
ListRemover_2
    LIST_ATTR = _nodeListe{}
    -> PointOnLineOverlayer [LINE]
LengthCalculator_2
    DIM = 2
    MULT = 1
    LEN_ATTR = _length
    -> CoordinateCounter
CoordinateCounter
    CNT_ATTR = _coordcount
    -> Tester_4
Tester_4
    TEST_LIST = &_length,!=,0,&_coordcount,>,1
    TEST_MODE = Automatic
    TEST_CLAUSE:
      TEST "@Value(_length)" != "0"
      TEST "@Value(_coordcount)" > "1"
    BOOL_OP = AND
    TEST_DESCRIPTION = ""
    PASSED -> Lenker (output)
Lenker (output)

Bookmark: Finner noder som tilhører kun 1 lenke
ListElementCounter
    LIST_NAME = _node_angle{}
    CNT_ATTR = _element_count
    -> TestFilter_3
Note: Kun ett element i lista / --> Endenode
TestFilter_3
    TEST_LIST = BOOL_OP,OR,COMPOSITE_TEST,<Unused>,TEST_CLAUSE,"TEST @Value(_element_count) = 1",Endenode
    DEFAULT_VALUE = <UNFILTERED>
    Endenode -> ListExploder
ListExploder
    LIST_ATTR = _node_angle{}
    ATTR_CONFLICT_RES = Use Incoming List
    ATTR_ACCUM_MODE = Merge Incoming List
    INDEX_ATTR = _element_index
    ELEMENTS -> AttributeCreator_3
    <REJECTED> -> AttributeCreator_3
Note: Identifiserer lenken
AttributeCreator_3
    ATTR_TABLE = SET_TO _node_arc_id = abs(@Value(fme_arc_id))
    -> AttributeKeeper
AttributeKeeper
    KEEP_ATTRS = _node_arc_id,_node_number,fme_arc_id,medium
    -> FeatureMerger [SUPPLIER]

Bookmark: Identifiserer hvilken ende av lenka noden gjelder
TestFilter_2
    TEST_LIST = TEST_CLAUSE,"TEST @Value(_node_number) = @Value(_from_node)",TEST_LIST,"&_node_number,=,&_from_node",TEST_MODE,Automatic,BOOL_OP,OR,Start,TEST_CLAUSE,"TEST @Value(_node_number) = @Value(_to_node)",TEST_LIST,"&_node_number,=,&_to_node",TEST_MODE,Automatic,BOOL_OP,OR,Slutt
    DEFAULT_VALUE = <UNFILTERED>
    Start -> AttributeCreator
    Slutt -> AttributeCreator_2
AttributeCreator
    ATTR_TABLE:
      SET_TO _vertexIdx = 0
      SET_TO _posisjon = Start
    -> CoordinateExtractor
AttributeCreator_2
    ATTR_TABLE:
      SET_TO _vertexIdx = -1
      SET_TO _posisjon = Slutt
    -> CoordinateExtractor

Bookmark: Lager nodepunktet
CoordinateExtractor
    Z_ATTR = _zN
    Y_ATTR = _yN
    Z_DEFAULT = -9999
    IND = @Value(_vertexIdx)
    MODE = Specify Coordinate
    X_ATTR = _xN
    -> VertexCreator_2
VertexCreator_2
    MODE_NAME = Replace with Point
    YVAL = @Value(_yN)
    XVAL = @Value(_xN)
    -> AttributeKeeper_3
AttributeKeeper_3
    KEEP_ATTRS = _BlindID,_posisjon,_vertexIdx,medium
    -> NeighborFinder_2 [BASE]

Bookmark: Finner ny posisjon for noder som ligger nær en annen lenke
Note: Finner nærliggende lenker / til den aktuelle noden, med samme medium
NeighborFinder_2
    TREAT_POLYGON_AS = Lines
    INSERT_VERTEX = No
    CANDIDATES_FIRST = No
    ATTR_CONFLICT_RES = Use Base
    MAX = $(dXYlim)
    MODE = Bases and Candidates
    ATTR_ACCUM_MODE = Merge Candidate
    GROUP_BY = medium
    CLOSE_LIST_NAME = _lenkeListe
    MATCHED -> AttributeRemover_2
AttributeRemover_2
    REMOVE_ATTRS = _angle,_candidate_label_angle,_closest_base_y,_distance,medium,_closest_base_x,_candidate_angle,_closest_candidate_y,_closest_candidate_x
    -> ListSorter
ListSorter
    SRC_LIST = _lenkeListe{}.distance
    ORDER = Ascending
    TYPE = Numeric
    -> ListSearcher
ListSearcher
    LIST_ATTR = _lenkeListe{}.distance
    ATTR_VALUE = 0
    SEARCH_TYPE = First greater than
    INDEX_ATTR = _list_index
    FOUND -> Tester_2
Note: Tar kun med de nodene / som har en nærliggende lenke / innenfor avstand > 0
Tester_2
    TEST_LIST = &_list_index,!=,-1
    TEST_MODE = Automatic
    TEST_CLAUSE = TEST "@Value(_list_index)" != "-1"
    BOOL_OP = OR
    TEST_DESCRIPTION = ""
    PASSED -> ListIndexer
Note: Finner nærmeste > 0
ListIndexer
    LIST_ATTR = _lenkeListe{}
    INDEX = @Value(_list_index)
    -> 2DPointReplacer
    -> AttributeKeeper_5
AttributeKeeper_5
    KEEP_ATTRS = _BlindID,_posisjon,_vertexIdx,closest_candidate_x,closest_candidate_y
    -> FeatureMerger_2 [SUPPLIER]
Note: Lager krysningspunkt
2DPointReplacer
    XVALATTR = @Value(closest_candidate_x)
    YVALATTR = @Value(closest_candidate_y)
    POINT -> AttributeKeeper_4

Bookmark: Flytter løse endepunkter til punkt på nærliggende lenker
Note: Kobler nodene med / til lenkene igjen
FeatureMerger_2
    MERGE_TYPE = Attributes Only
    REFERATTR = _BlindID
    BUILD_INCOMPLETE = No
    PROCESS_DUPS = No
    REFEEATTR = _BlindID
    LIST_NAME = _nodeListe
    COMPLETE -> ListElementCounter_2
    INCOMPLETE -> AttributeRemover_3
ListElementCounter_2
    LIST_NAME = _nodeListe{}
    CNT_ATTR = _element_count
    -> ListIndexer_2
ListIndexer_2
    LIST_ATTR = _nodeListe{}
    INDEX = 0
    -> VertexModifier_4
Note: Flytter første løse endepunkt / til punkt fra nærliggende lenke
VertexModifier_4
    VAL_3 = NULL
    VAL_2 = @Value(closest_candidate_y)
    VAL = @Value(_vertexIdx)
    XX = @Value(closest_candidate_x)
    -> Tester_6
Note: Flytter første løse endepunkt / til punkt fra nærliggende lenke
Tester_6
    TEST_LIST = &_element_count,=,2
    TEST_MODE = Automatic
    TEST_CLAUSE = TEST "@Value(_element_count)" = "2"
    BOOL_OP = OR
    TEST_DESCRIPTION = ""
    PASSED -> ListIndexer_3
    FAILED -> AttributeRemover_3
ListIndexer_3
    LIST_ATTR = _nodeListe{}
    INDEX = 1
    -> VertexModifier_2
Note: Flytter andre løse endepunkt til punkt fra nærliggende lenke
VertexModifier_2
    VAL_3 = NULL
    VAL_2 = @Value(closest_candidate_y)
    VAL = @Value(_vertexIdx)
    XX = @Value(closest_candidate_x)
    -> AttributeRemover_3

Bookmark: Splitter nærliggende lenker
Note: Splitter linje i krysningspunkt
PointOnLineOverlayer
    OV_ATTR = _overlaps
    GRP_BY = medium
    TOLERANCE = $(dXYlim)
    LINE -> LengthCalculator_2

FME custom transformer Segments
Creates a list of segments with RoladLinkID, from meassure and to-meassure from an overlay between event tables

Parameters:
- RoadLinkID =   # " " RoadLinkID
- FromVal =   # " " FromVal
- ToVal =   # " " ToVal

Event_Tables (input)
    -> AttributeCreator_2
Note: Loop for creating unique table of segments
UniqeSegments
    __COMPOUND_PARAMETERS = -
    Unique_Segments -> AttributeManager
AttributeManager
    ATTR_TABLE = SET_TO _SegId = @Value(RoadLinkID)_@Value(FromVal)_@Value(ToVal)
    -> Unique_Segment_List (output)
Unique_Segment_List (output)

Bookmark: Link ID and meassure attributes
AttributeCreator_2
    ATTR_TABLE:
      SET_TO RoadLinkID = $(RoadLinkID)
      SET_TO FromVal = $(FromVal)
      SET_TO ToVal = $(ToVal)
    -> AttributeKeeper
AttributeKeeper
    KEEP_ATTRS = RoadLinkID,FromVal,ToVal
    -> ATTRIBUTERENAMER_3
    -> ATTRIBUTERENAMER_4

Bookmark: Create a list of all unique breakpoints pr RoadLinkID
Note: From
ATTRIBUTERENAMER_3: AttributeRenamer
    ATTR_TABLE = RENAME_SET_DEFAULT FromVal > BREAKPOINT
    -> AttributeKeeper_2
Note: To
ATTRIBUTERENAMER_4: AttributeRenamer
    ATTR_TABLE = RENAME_SET_DEFAULT ToVal > BREAKPOINT
    -> AttributeKeeper_2
AttributeKeeper_2
    KEEP_ATTRS = RoadLinkID,BREAKPOINT
    -> DuplicateFilter
DuplicateFilter
    INPUT_ORDERED_CHOICE = No
    KEYATTR = RoadLinkID BREAKPOINT
    UNIQUE -> ListBuilder
ListBuilder
    GRP_BY = RoadLinkID
    LIST_NAME = _Bp_list
    -> ListSorter
ListSorter
    SRC_LIST = _Bp_list{}.BREAKPOINT
    ORDER = Ascending
    TYPE = Numeric
    -> ListElementCounter
ListElementCounter
    LIST_NAME = _Bp_list{}
    CNT_ATTR = _element_count
    -> AttributeManager_2
AttributeManager_2
    ATTR_TABLE:
      SET_TO _maxIdx = @Evaluate(@Evaluate(@Value(_element_count)-1))
      REMOVE _element_count
      SET_TO _idx = 0
    -> UniqeSegments [BREAKPOINTLIST]

FME custom transformer Sykkelforbud

Parameters:
- TNE_sl3 = C:\DATA\TNE\data\tne_local.db   # Lokal TNE

Område (input)
    -> AttributeExposer
    -> BoundsExtractor
AttributeExposer
    ATTR_LIST = _where
    -> FeatureReader_2 [INITIATOR]
Note: Fagdata fra TNE
FeatureReader_2
    DATASET = $(TNE_sl3)
    ATTR_ACCUM_MODE = Only Use Result
    COMBINE_GEOM = Use Result
    WHERE = @Value(_where)
    FORMAT = SPATIALITE
    SUPPORTED_SPATIAL_INTERACTIONS = ENVELOPE_INTERSECT%ENVELOPE_INTERSECT%INTERSECTS%CONTAINS%CROSSES%DISJOINT%EQUALS%OVERLAPS%TOUCHES%WITHIN
    SPATIALITE_QUERY_FEATURE_TYPES_FOR_MERGE_FILTERS = Yes
    OUTPUT_FEATURES_DISPLAY = Schema and Data Features
    ATTRIBUTES = belysningsanlegg,"objectid,netobjecttv_id,from_date,to_date,seq_no,ba_200026_oid,ba_200246_oid,ba_200558_oid,ba_201440_oid,brom_1271,type_1144,navns_8396,bygge_8399,tenns_8404,mast_3700,lost_3697,stfb_3755,stve_3760,eier_5810,eiern_8397,vhan_1554,jevnk_8743,lumkr_8740,avin_1714,tilsk_8398,utedr_8400,vdb_i_7656,route_id,from_measure,to_measure,side,topology_level,dimmi_10001,shape_len",bruksklasse,"objectid,netobjecttv_id,from_date,to_date,seq_no,ba_200239_oid,bk_5179,bkvin_5180,bktel_5181,akste_7576,mvgl_5186,brsp_5184,strbe_5183,strsp_8800,strto_8801,beskr_9308,beskr_9309,merk_5182,vektm_9125,lengm_9126,vektt_9127,lengt_9128,t100tv_9254,mobkr_9256,maxle_8804,kjtle_8805,maxto_7542,maxto_7577,maxto_7578,maxto_7579,vdb_i_7670,route_id,from_measure,to_measure,topology_level,strbe_10721,mvvin_10722,mvlin_10723,shape_len",curvesegment,"objectid,reflink_oid,from_date,to_date,from_measure,to_measure,seg_date,length,class_code,object_code,medium,quality_method,quality_accuracy,quality_visibility,quality_method_height,quality_accuracy_height,quality_tolerance,municipality,shape_len",fartsgrense,"objectid,netobjecttv_id,from_date,to_date,seq_no,ba_200272_oid,ba_200952_oid,ba_201829_oid,fagr_2021,vtnr_1891,vtdt_5124,journ_9155,vrfg_5125,gfdt_5127,tidb_2071,vdb_i_7671,route_id,from_measure,to_measure,lanecode,topology_level,shape_len",feltstrekning,"objectid,netobjecttv_id,from_date,to_date,seq_no,flto_5528,route_id,from_measure,to_measure,topology_level,shape_len",fortau,"objectid,netobjecttv_id,from_date,to_date,seq_no,ba_200235_oid,ba_200280_oid,ba_200569_oid,ba_201418_oid,ba_201692_oid,vhan_5638,eier_7994,bel_5637,vdb_i_7633,vaka_1830,route_id,from_measure,to_measure,side,topology_level,ba_202020_oid,bygge_10295,bredg_2241,bredh_10717,punkt_10718,ba_202126_oid,shape_len",gate,"objectid,netobjecttv_id,from_date,to_date,seq_no,ht_200699_oid,ba_201568_oid,gtkd_4588,gtnv_4589,route_id,from_measure,to_measure,side,topology_level,sidev_9793,shape_len",ikfb,"objectid,netobjecttv_id,from_date,to_date,seq_no,ba_200801_oid,mrk_5476,sknr_5475,route_id,from_measure,to_measure,side,direction,lanecode,topology_level,shape_len",motorveg,"objectid,netobjecttv_id,from_date,to_date,seq_no,ba_200790_oid,mvegt_5378,vtakd_5377,vedta_5376,route_id,from_measure,to_measure,topology_level,journ_9485,bygge_10328,shape_len",trafikkmengde,"objectid,netobjecttv_id,from_date,to_date,seq_no,ba_200670_oid,ba_201812_oid,tadt_4623,langx_4624,ar_4621,opfr_6843,grlg_4625,anid_4620,trafa_7477,tppm_5219,tpsd_5222,fadt_5220,flng_5221,kpar_5223,mfak_4622,aadts_7475,aadts_7476,vdb_i_7804,route_id,from_measure,to_measure,topology_level,shape_len",tunnel,"objectid,netobjecttv_id,from_date,to_date,seq_no,ba_200710_oid,ba_200711_oid,ba_200714_oid,ba_200752_oid,ba_200778_oid,ba_200785_oid,navn_5225,tunne_9306,tunne_9134,parhl_3947,lensk_8945,lenlo_8150,lenra_8151,under_9517,sykke_9518,tlfvt_3917,albra_3918,kbsn_3915,kbng_3916,brann_9507,restr_9131,mrkre_9506,mksy_3913,brutu_9329,route_id,measure,topology_level,xlht_3947,bpgk_3919,bplan_9132,upba_3914,sngt_3917,avfb_3918,apnea_10383,ba_202110_oid",tunnellop,"objectid,netobjecttv_id,from_date,to_date,seq_no,kateg_8944,tunlp_1977,type_1130,leng_1317,area_1367,bred_3897,apnin_8356,usjo_5272,skfb_3899,innbe_7864,brutu_9305,innr_2178,merk_5286,vdb_i_7642,ba_200031_oid,ba_200061_oid,ba_200167_oid,ba_200187_oid,ba_200201_oid,ba_200202_oid,ba_200203_oid,ba_200205_oid,ba_200407_oid,ba_200464_oid,ba_200739_oid,ba_200740_oid,ba_200741_oid,ba_200742_oid,ba_200743_oid,ba_200744_oid,ba_200745_oid,ba_200746_oid,ba_200747_oid,ba_200749_oid,ba_200751_oid,ba_200755_oid,ba_200757_oid,ba_200759_oid,ba_200760_oid,ba_200761_oid,ba_200762_oid,ba_200763_oid,ba_200764_oid,ba_200765_oid,ba_200766_oid,ba_200767_oid,ba_200768_oid,ba_200769_oid,ba_200770_oid,ba_200772_oid,ba_200774_oid,ba_200775_oid,ba_200776_oid,ba_200777_oid,ba_200779_oid,ba_200781_oid,ba_200782_oid,ba_200784_oid,ba_200786_oid,ba_200811_oid,ba_200812_oid,ba_200813_oid,ba_200815_oid,ba_200816_oid,ba_200817_oid,ba_200818_oid,ba_200819_oid,ba_200839_oid,ba_201427_oid,ba_201637_oid,ba_201815_oid,ba_201819_oid,ba_201830_oid,ba_201833_oid,ba_201868_oid,ba_201869_oid,ba_201874_oid,ba_201877_oid,ba_201878_oid,navn_1081,route_id,from_measure,to_measure,side,lanecode,topology_level,ba_201885_oid,ba_201893_oid,ba_201894_oid,ba_200081_oid,ba_201971_oid,ba_202006_oid,ba_202035_oid,ba_202041_oid,ba_202042_oid,ba_202046_oid,ba_202038_oid,ba_202039_oid,ba_202083_oid,ba_202103_oid,rehab_10693,shape_len",vegfunksjon,"objectid,netobjecttv_id,from_date,to_date,seq_no,ba_200705_oid,vf_5178,route_id,from_measure,to_measure,topology_level,shape_len",vegreferanse,"objectid,netobjecttv_id,from_date,to_date,seq_no,fynr_4591,kmnr_4592,vktg_4566,vsov_4570,vgnr_4568,hp_4569,vsts_4567,frmt_4571,tlmt_4572,brk1_4576,brk2_4577,vgtp_4574,fvkd_4573,enrg_4707,svtp_4575,mdat_4578,route_id,from_measure,to_measure,direction,topology_level,shape_len"
    FEATURETYPES = motorveg tunnellop
    INTERACT = Envelope Intersects
    motorveg -> AttributeKeeper_2
    tunnellop -> AttributeSplitter_2
AttributeKeeper_2
    KEEP_ATTRS = from_measure,to_measure,route_id
    -> BulkAttributeRenamer_2
BulkAttributeRenamer_2
    CASE_CHANGE_TYPE = upper
    ATTRCHOICE = All Attributes
    MODE_CHOICE = RENAME
    PATTERN_ACTION_DISP = CASECHANGE
    -> AttributeKeeper_3
BoundsExtractor
    ZMAX = _zmax
    YMIN = _ymin
    XMIN = _xmin
    XMAX = _xmax
    ZMIN = _zmin
    YMAX = _ymax
    -> HTTPCaller_2
Note: Henter tunneller med sykkelforbud / i valgt kommune
HTTPCaller_2
    TARGET_ATTR = _url_contents
    ERROR_ATTR = _error
    SAVE_FILE = Attribute
    RESPONSE_HEADER_LIST_ATTR = _headers
    VERIFY_SSL_CERTIFICATES = Yes
    TRANSFER_TIMEOUT_LENGTH = 90
    STATUS_CODE_ATTR = _http_status_code
    CONNECTION_TIMEOUT_LENGTH = 60
    USE_COOKIES = No
    TARGET_ATTR_ENCODING = auto-detect
    HTTP_METHOD = GET
    TARGET_URL = https://www.vegvesen.no/nvdb/api/sok?kriterie={"lokasjon":{"bbox": "@Value(_xmin),@Value(_ymin),@Value(_xmax),@Value(_ymax)"},"objektTyper":[{"id":581,"antall":"250","filter":[{ type: "Sykkelforbud", operator: "=", verdi: ["Ja"]}]}]}
    FOLLOW_REDIRECTS = Yes
    CUSTOM_HEADERS = Accept;application/vnd.vegvesen.nvdb-v1+xml
    -> XMLFragmenter
Note: Finner assosiasjoner
XMLFragmenter
    FLATTEN_OPTIONS = <structure separator="." map-empty-elements="yes" matched-prefix="attributes" matched-attributes="yes" cardinality="+{?}" structure-prefix="" child-position-attribute="" except-expression="" ui-mode="basic" matched-ancestor-attributes=""/>
    XML_SOURCE_TYPE = Attribute with XML document
    EMBEDDED_EXPRESSIONS_EXCEPT = resultater
    FEATURE_TYPES_FORMAT_NAME = XML
    MERGE_ATTRS = No
    NEW_ATTRIBUTES = assosiasjon{}.relasjon.uri assosiasjon{}.relasjon.typeNavn
    EMBEDDED_EXPRESSIONS = assosiasjoner
    ATTRIBUTE_XML = _url_contents
    FRAGMENTS -> ListExploder
Note: Ekspanderer assosiasjonsliste
ListExploder
    LIST_ATTR = assosiasjon{}
    ATTR_CONFLICT_RES = Use Incoming List
    ATTR_ACCUM_MODE = Merge Incoming List
    INDEX_ATTR = _element_index
    ELEMENTS -> TestFilter
    <REJECTED> -> BulkAttributeRenamer
BulkAttributeRenamer
    REPLACE_STR = assosiasjon.
    ATTRCHOICE = All Attributes
    CASE_DISP = YES
    MODE_CHOICE = RENAME
    PATTERN_ACTION_DISP = REMOVEPREFIX
    -> TestFilter
Note: Assosierte tunnelløp
TestFilter
    TEST_LIST = BOOL_OP,OR,COMPOSITE_TEST,<Unused>,TEST_CLAUSE,"TEST @Value(relasjon.typeNavn) = Tunnelløp",Tunnelløp
    DEFAULT_VALUE = <UNFILTERED>
    Tunnelløp -> AttributeSplitter_3
Note: Tunnelløp med sykkelforbud
FeatureMerger
    JOIN_KEYS = @Value(NVDB_ID) @Value(NVDB_ID) AUTO
    ATTR_CONFLICT_RES = Use Requestor
    PROCESS_DUPS = No
    MERGE_TYPE = Attributes Only
    ATTR_ACCUM_MODE = Merge Supplier
    SUPPLIERS_FIRST = No
    IGNORE_NULLS = Yes
    REJECT_NULL_MISSING_KEYS = No
    MERGED -> AttributeKeeper_7

Bookmark: Segmenterer Motorveg og Tunnelløp
AttributeKeeper_3
    KEEP_ATTRS = ROUTE_ID,FROM_MEASURE,TO_MEASURE
    -> EO_SykkelforbudBelysning [Event_table_A]
AttributeKeeper_7
    KEEP_ATTRS = ROUTE_ID,TO_MEASURE,FROM_MEASURE
    -> EO_SykkelforbudBelysning [Event_table_B]
EO_SykkelforbudBelysning: EventOverlayer
    RoadLinkID = @Value(ROUTE_ID)
    FromVal = @Value(FROM_MEASURE)
    ToVal = @Value(TO_MEASURE)
    Common_Segments -> AttributeManager_3
    Only_A -> AttributeManager_3
    Only_B -> AttributeManager_3
AttributeManager_3
    ATTR_TABLE:
      SET_TO ROUTE_ID = @Value(RoadLinkID)
      SET_TO FROM_MEASURE = @Value(FromVal)
      SET_TO TO_MEASURE = @Value(ToVal)
      REMOVE RoadLinkID
      REMOVE _SegId
      REMOVE FromVal
      REMOVE ToVal
    -> Sykkelforbud (output)
Sykkelforbud (output)

Bookmark: Ordner NVDB-id
AttributeSplitter_2
    DROP_EMPTY_PARTS = No
    ATTR_NAME = netobjecttv_id
    TRIM_OPTION = Both
    DELIMITER = :
    LIST_NAME = _list
    -> ListIndexer
ListIndexer
    LIST_ATTR = _list{}
    INDEX = 0
    -> AttributeManager_2
AttributeManager_2
    ATTR_TABLE:
      REMOVE _list{}
      RENAME_SET_VALUE _list > NVDB_ID
      REMOVE objectid
      REMOVE netobjecttv_id
      REMOVE from_date
      REMOVE to_date
      REMOVE seq_no
      REMOVE kateg_8944
      REMOVE tunlp_1977
      REMOVE type_1130
      REMOVE leng_1317
      REMOVE area_1367
      REMOVE bred_3897
      REMOVE apnin_8356
      REMOVE usjo_5272
      REMOVE skfb_3899
      REMOVE innbe_7864
      REMOVE brutu_9305
      REMOVE innr_2178
      REMOVE merk_5286
      REMOVE vdb_i_7642
      REMOVE ba_200031_oid
      REMOVE ba_200061_oid
      REMOVE ba_200167_oid
      REMOVE ba_200187_oid
      REMOVE ba_200201_oid
      REMOVE ba_200202_oid
      REMOVE ba_200203_oid
      REMOVE ba_200205_oid
      REMOVE ba_200407_oid
      REMOVE ba_200464_oid
      REMOVE ba_200739_oid
      REMOVE ba_200740_oid
      REMOVE ba_200741_oid
      REMOVE ba_200742_oid
      REMOVE ba_200743_oid
      REMOVE ba_200744_oid
      REMOVE ba_200745_oid
      REMOVE ba_200746_oid
      REMOVE ba_200747_oid
      REMOVE ba_200749_oid
      REMOVE ba_200751_oid
      REMOVE ba_200755_oid
      REMOVE ba_200757_oid
      REMOVE ba_200759_oid
      REMOVE ba_200760_oid
      REMOVE ba_200761_oid
      REMOVE ba_200762_oid
      REMOVE ba_200763_oid
      REMOVE ba_200764_oid
      REMOVE ba_200765_oid
      REMOVE ba_200766_oid
      REMOVE ba_200767_oid
      REMOVE ba_200768_oid
      REMOVE ba_200769_oid
      REMOVE ba_200770_oid
      REMOVE ba_200772_oid
      REMOVE ba_200774_oid
      REMOVE ba_200775_oid
      REMOVE ba_200776_oid
      REMOVE ba_200777_oid
      REMOVE ba_200779_oid
      REMOVE ba_200781_oid
      REMOVE ba_200782_oid
      REMOVE ba_200784_oid
      REMOVE ba_200786_oid
      REMOVE ba_200811_oid
      REMOVE ba_200812_oid
      REMOVE ba_200813_oid
      REMOVE ba_200815_oid
      REMOVE ba_200816_oid
      REMOVE ba_200817_oid
      REMOVE ba_200818_oid
      REMOVE ba_200819_oid
      REMOVE ba_200839_oid
      REMOVE ba_201427_oid
      REMOVE ba_201637_oid
      REMOVE ba_201815_oid
      REMOVE ba_201819_oid
      REMOVE ba_201830_oid
      REMOVE ba_201833_oid
      REMOVE ba_201868_oid
      REMOVE ba_201869_oid
      REMOVE ba_201874_oid
      REMOVE ba_201877_oid
      REMOVE ba_201878_oid
      REMOVE navn_1081
      RENAME_SET_VALUE route_id > ROUTE_ID
      RENAME_SET_VALUE from_measure > FROM_MEASURE
      RENAME_SET_VALUE to_measure > TO_MEASURE
      REMOVE side
      REMOVE lanecode
      REMOVE topology_level
      REMOVE ba_201885_oid
      REMOVE ba_201893_oid
      REMOVE ba_201894_oid
      REMOVE ba_200081_oid
      REMOVE ba_201971_oid
      REMOVE ba_202006_oid
      REMOVE ba_202035_oid
      REMOVE ba_202041_oid
      REMOVE ba_202042_oid
      REMOVE ba_202046_oid
      REMOVE ba_202038_oid
      REMOVE ba_202039_oid
      REMOVE ba_202083_oid
      REMOVE ba_202103_oid
      REMOVE rehab_10693
      REMOVE shape_len
    -> FeatureMerger [REQUESTOR]

Bookmark: Ordner NVDB-id
AttributeSplitter_3
    DROP_EMPTY_PARTS = No
    ATTR_NAME = relasjon.uri
    TRIM_OPTION = Both
    DELIMITER = /
    LIST_NAME = _list
    -> ListIndexer_2
ListIndexer_2
    LIST_ATTR = _list{}
    INDEX = 3
    -> AttributeManager
AttributeManager
    ATTR_TABLE:
      REMOVE relasjon.uri
      REMOVE relasjon.typeNavn
      REMOVE xml_fragment
      REMOVE xml_id
      REMOVE xml_matched_element
      REMOVE xml_parent_id
      REMOVE xml_parent_child_pos
      REMOVE _element_index
      REMOVE fme_rejection_code
      REMOVE _list{}
      RENAME_SET_VALUE _list > NVDB_ID
    -> FeatureMerger [SUPPLIER]

FME custom transformer ElevationInterpolator

INPUT (input)
    -> DimensionExtractor_2
Note: DimensionExtractor
DimensionExtractor_2
    DIM_ATTR = _dimension
    -> CoordinateExtractor_5
AttributeFilter
    ATTR_NAME = _dimension
    ATTR_VALUES = <EMPTY>,<MISSING>,<NULL>,<UNFILTERED>,2,3
    2 -> NodeElevation [2D_Lines]
    3 -> NodeElevation [3D_Lines]
    3 -> AttributeRemover
    3 -> SurfaceDraper_2 [POINTS/LINES]
Note: Get node elevation from nearby nodes, / and interpolate line elevation if both nodes are matched
NodeElevation
    __COMPOUND_PARAMETERS = -
    InterpolatedTo3D -> AttributeRemover
    InterpolatedTo3D -> SurfaceDraper_2 [POINTS/LINES]
    2D_Lines -> SurfaceDraper_2 [DRAPE_FEATURES]
Note: Drape remaining 2D lines on / a surface based on the 3D Lines
SurfaceDraper_2
    DRAPE_TYPE = VERTEX
    INTERPOLATION_TYPE = CONSTANT
    ADDZ_TYPE = Replace Z
    TOLERANCE = 0
    DRAPED_FEATURES -> TestFilter
AttributeRemover
    LIST_ATTRS = measure_list{}
    REMOVE_ATTRS = _xmax,_xmin,_ymax,_ymin,_zmax,_zmin,_dimension,_startX,_startY,_endX,_endY,_LinkID,_StartNodeZ,_position,_overlaps,_EndNodeZ,_x,_y,_z,_startZ,_endZ
    -> OUTPUT (output)
OUTPUT (output)

Bookmark: Node coordinates
Note: Start coordinates
CoordinateExtractor_5
    Z_ATTR = _startZ
    Y_ATTR = _startY
    Z_DEFAULT = -9999
    IND = 0
    MODE = Specify Coordinate
    X_ATTR = _startX
    -> CoordinateExtractor_6
Note: End coordinates
CoordinateExtractor_6
    Z_ATTR = _endZ
    Y_ATTR = _endY
    Z_DEFAULT = -9999
    IND = -1
    MODE = Specify Coordinate
    X_ATTR = _endX
    -> AttributeFilter

Bookmark: Interpolate elevation
TestFilter
    TEST_LIST:
      TEST_CLAUSE,"TEST @Value(_StartNodeZ) != NULL
      TEST @Value(_EndNodeZ) = NULL",TEST_LIST,"&_StartNodeZ,!=,NULL,&_EndNodeZ,=,NULL",TEST_MODE,Automatic,BOOL_OP,AND,Start_node,TEST_CLAUSE,"TEST @Value(_StartNodeZ) = NULL
      TEST @Value(_EndNodeZ) != NULL",TEST_LIST,"&_StartNodeZ,=,NULL,&_EndNodeZ,!=,NULL",TEST_MODE,Automatic,BOOL_OP,AND,End_node
    DEFAULT_VALUE = <UNFILTERED>
    Start_node -> CoordinateExtractor_4
    End_node -> CoordinateExtractor_3
    <UNFILTERED> -> AttributeRemover
Note: Start node elevation from NodeElevation, / get end node elevation from SurfaceDraper
CoordinateExtractor_4
    Z_ATTR = _z
    Y_ATTR = _y
    Z_DEFAULT = -9999
    IND = -1
    MODE = Specify Coordinate
    X_ATTR = _x
    -> AttributeCreator
AttributeCreator
    ATTR_TABLE = SET_TO _EndNodeZ = @Value(_z)
    -> 3DInterpolator
Note: End node elevation from NodeElevation, / get start node elevation from SurfaceDraper
CoordinateExtractor_3
    Z_ATTR = _z
    Y_ATTR = _y
    Z_DEFAULT = -9999
    IND = 0
    MODE = Specify Coordinate
    X_ATTR = _x
    -> AttributeCreator_2
AttributeCreator_2
    ATTR_TABLE = SET_TO _StartNodeZ = @Value(_z)
    -> 3DInterpolator
Note: Interpolate elevation, force one end to / be at the elevation of the matched node
3DInterpolator
    ZSTARTATTR = @Value(_StartNodeZ)
    ZENDATTR = @Value(_EndNodeZ)
    -> AttributeRemover

FME custom transformer Segmentering

Sykkelforbud (input)
    -> AttributeManager
AttributeManager
    ATTR_TABLE = SET_TO sykkelforbud = Ja
    -> EO_SykkelforbudBelysning [Event_table_A]
Belysning (input)
    -> AttributeManager_3
AttributeManager_3
    ATTR_TABLE:
      SET_TO belysning = Ja
      REMOVE OBJECTID
      REMOVE NETOBJECTTV_ID
      REMOVE FROM_DATE
      REMOVE TO_DATE
      REMOVE SEQ_NO
      REMOVE BA_200026_OID
      REMOVE BA_200246_OID
      REMOVE BA_200558_OID
      REMOVE BA_201440_OID
      REMOVE BROM_1271
      REMOVE TYPE_1144
      REMOVE NAVNS_8396
      REMOVE BYGGE_8399
      REMOVE TENNS_8404
      REMOVE MAST_3700
      REMOVE LOST_3697
      REMOVE STFB_3755
      REMOVE STVE_3760
      REMOVE EIER_5810
      REMOVE EIERN_8397
      REMOVE VHAN_1554
      REMOVE JEVNK_8743
      REMOVE LUMKR_8740
      REMOVE AVIN_1714
      REMOVE TILSK_8398
      REMOVE UTEDR_8400
      REMOVE VDB_I_7656
      REMOVE SIDE
      REMOVE TOPOLOGY_LEVEL
      REMOVE DIMMI_10001
      REMOVE SHAPE_LEN
      REMOVE BA_200235_OID
      REMOVE BA_200280_OID
      REMOVE BA_200569_OID
      REMOVE BA_201418_OID
      REMOVE BA_201692_OID
      REMOVE VHAN_5638
      REMOVE EIER_7994
      REMOVE BEL_5637
      REMOVE VDB_I_7633
      REMOVE VAKA_1830
      REMOVE BA_202020_OID
      REMOVE BYGGE_10295
      REMOVE BREDG_2241
      REMOVE BREDH_10717
      REMOVE PUNKT_10718
      REMOVE BA_202126_OID
      REMOVE _COUNT
      REMOVE _TIMESTAMP
      REMOVE _WHERE
      REMOVE FME_FEATURE_TYPE_NAME
      REMOVE ATTRIBUTE{}.NAME
      REMOVE ATTRIBUTE{}.FME_DATA_TYPE
      REMOVE ATTRIBUTE{}.NATIVE_DATA_TYPE
      REMOVE FME_FORMAT_SHORT_NAME
      REMOVE FME_FORMAT_LONG_NAME
      REMOVE BA_200801_OID
      REMOVE MRK_5476
      REMOVE SKNR_5475
      REMOVE DIRECTION
      REMOVE LANECODE
      REMOVE HT_200699_OID
      REMOVE BA_201568_OID
      REMOVE GTKD_4588
      REMOVE GTNV_4589
      REMOVE SIDEV_9793
      REMOVE BA_200670_OID
      REMOVE BA_201812_OID
      REMOVE TADT_4623
      REMOVE LANGX_4624
      REMOVE AR_4621
      REMOVE OPFR_6843
      REMOVE GRLG_4625
      REMOVE ANID_4620
      REMOVE TRAFA_7477
      REMOVE TPPM_5219
      REMOVE TPSD_5222
      REMOVE FADT_5220
      REMOVE FLNG_5221
      REMOVE KPAR_5223
      REMOVE MFAK_4622
      REMOVE AADTS_7475
      REMOVE AADTS_7476
      REMOVE VDB_I_7804
      REMOVE FYNR_4591
      REMOVE KMNR_4592
      REMOVE VKTG_4566
      REMOVE VSOV_4570
      REMOVE VGNR_4568
      REMOVE HP_4569
      REMOVE VSTS_4567
      REMOVE FRMT_4571
      REMOVE TLMT_4572
      REMOVE BRK1_4576
      REMOVE BRK2_4577
      REMOVE VGTP_4574
      REMOVE FVKD_4573
      REMOVE ENRG_4707
      REMOVE SVTP_4575
      REMOVE MDAT_4578
      REMOVE FLTO_5528
      REMOVE BA_200272_OID
      REMOVE BA_200952_OID
      REMOVE BA_201829_OID
      REMOVE FAGR_2021
      REMOVE VTNR_1891
      REMOVE VTDT_5124
      REMOVE JOURN_9155
      REMOVE VRFG_5125
      REMOVE GFDT_5127
      REMOVE TIDB_2071
      REMOVE VDB_I_7671
      REMOVE fme_feature_type
    -> EO_SykkelforbudBelysning [Event_table_B]
EO_SykkelforbudBelysning: EventOverlayer
    RoadLinkID = @Value(ROUTE_ID)
    FromVal = @Value(FROM_MEASURE)
    ToVal = @Value(TO_MEASURE)
    Common_Segments -> AttributeManager_4
    Only_A -> AttributeManager_4
    Only_B -> AttributeManager_4
Note: Rekkefølgen på segmentering er ut i fra anntatt antall segmenter, av hensyn til hastighet. Færrest mulig segmenter som skal prosesseres flere ganger
AttributeManager_4
    ATTR_TABLE:
      SET_TO ROUTE_ID = @Value(RoadLinkID)
      SET_TO FROM_MEASURE = @Value(FromVal)
      SET_TO TO_MEASURE = @Value(ToVal)
      REMOVE RoadLinkID
      REMOVE FromVal
      REMOVE ToVal
      REMOVE _SegId
    -> EO_Fortau [Event_table_A]
Fortau (input)
    -> AttributeManager_5
AttributeManager_5
    ATTR_TABLE:
      SET_TO fortau = Ja
      REMOVE OBJECTID
      REMOVE NETOBJECTTV_ID
      REMOVE FROM_DATE
      REMOVE TO_DATE
      REMOVE SEQ_NO
      REMOVE BA_200026_OID
      REMOVE BA_200246_OID
      REMOVE BA_200558_OID
      REMOVE BA_201440_OID
      REMOVE BROM_1271
      REMOVE TYPE_1144
      REMOVE NAVNS_8396
      REMOVE BYGGE_8399
      REMOVE TENNS_8404
      REMOVE MAST_3700
      REMOVE LOST_3697
      REMOVE STFB_3755
      REMOVE STVE_3760
      REMOVE EIER_5810
      REMOVE EIERN_8397
      REMOVE VHAN_1554
      REMOVE JEVNK_8743
      REMOVE LUMKR_8740
      REMOVE AVIN_1714
      REMOVE TILSK_8398
      REMOVE UTEDR_8400
      REMOVE VDB_I_7656
      RENAME_SET_VALUE SIDE > fortauside
      REMOVE TOPOLOGY_LEVEL
      REMOVE DIMMI_10001
      REMOVE SHAPE_LEN
      REMOVE BA_200235_OID
      REMOVE BA_200280_OID
      REMOVE BA_200569_OID
      REMOVE BA_201418_OID
      REMOVE BA_201692_OID
      REMOVE VHAN_5638
      REMOVE EIER_7994
      REMOVE BEL_5637
      REMOVE VDB_I_7633
      REMOVE VAKA_1830
      REMOVE BA_202020_OID
      REMOVE BYGGE_10295
      REMOVE BREDG_2241
      REMOVE BREDH_10717
      REMOVE PUNKT_10718
      REMOVE BA_202126_OID
      REMOVE _COUNT
      REMOVE _TIMESTAMP
      REMOVE _WHERE
      REMOVE FME_FEATURE_TYPE_NAME
      REMOVE ATTRIBUTE{}.NAME
      REMOVE ATTRIBUTE{}.FME_DATA_TYPE
      REMOVE ATTRIBUTE{}.NATIVE_DATA_TYPE
      REMOVE FME_FORMAT_SHORT_NAME
      REMOVE FME_FORMAT_LONG_NAME
      REMOVE BA_200801_OID
      REMOVE MRK_5476
      REMOVE SKNR_5475
      REMOVE DIRECTION
      REMOVE LANECODE
      REMOVE HT_200699_OID
      REMOVE BA_201568_OID
      REMOVE GTKD_4588
      REMOVE GTNV_4589
      REMOVE SIDEV_9793
      REMOVE BA_200670_OID
      REMOVE BA_201812_OID
      REMOVE TADT_4623
      REMOVE LANGX_4624
      REMOVE AR_4621
      REMOVE OPFR_6843
      REMOVE GRLG_4625
      REMOVE ANID_4620
      REMOVE TRAFA_7477
      REMOVE TPPM_5219
      REMOVE TPSD_5222
      REMOVE FADT_5220
      REMOVE FLNG_5221
      REMOVE KPAR_5223
      REMOVE MFAK_4622
      REMOVE AADTS_7475
      REMOVE AADTS_7476
      REMOVE VDB_I_7804
      REMOVE FYNR_4591
      REMOVE KMNR_4592
      REMOVE VKTG_4566
      REMOVE VSOV_4570
      REMOVE VGNR_4568
      REMOVE HP_4569
      REMOVE VSTS_4567
      REMOVE FRMT_4571
      REMOVE TLMT_4572
      REMOVE BRK1_4576
      REMOVE BRK2_4577
      REMOVE VGTP_4574
      REMOVE FVKD_4573
      REMOVE ENRG_4707
      REMOVE SVTP_4575
      REMOVE MDAT_4578
      REMOVE FLTO_5528
      REMOVE BA_200272_OID
      REMOVE BA_200952_OID
      REMOVE BA_201829_OID
      REMOVE FAGR_2021
      REMOVE VTNR_1891
      REMOVE VTDT_5124
      REMOVE JOURN_9155
      REMOVE VRFG_5125
      REMOVE GFDT_5127
      REMOVE TIDB_2071
      REMOVE VDB_I_7671
      REMOVE fme_feature_type
    -> EO_Fortau [Event_table_B]
EO_Fortau: EventOverlayer
    RoadLinkID = @Value(ROUTE_ID)
    FromVal = @Value(FROM_MEASURE)
    ToVal = @Value(TO_MEASURE)
    Common_Segments -> AttributeManager_6
    Only_A -> AttributeManager_6
    Only_B -> AttributeManager_6
AttributeManager_6
    ATTR_TABLE:
      SET_TO ROUTE_ID = @Value(RoadLinkID)
      SET_TO FROM_MEASURE = @Value(FromVal)
      SET_TO TO_MEASURE = @Value(ToVal)
      REMOVE RoadLinkID
      REMOVE FromVal
      REMOVE ToVal
      REMOVE _SegId
    -> EO_IKFB [Event_table_A]
InnkjøringForbudt (input)
    -> AttributeManager_2
AttributeManager_2
    ATTR_TABLE:
      REMOVE OBJECTID
      REMOVE NETOBJECTTV_ID
      REMOVE FROM_DATE
      REMOVE TO_DATE
      REMOVE SEQ_NO
      REMOVE BA_200026_OID
      REMOVE BA_200246_OID
      REMOVE BA_200558_OID
      REMOVE BA_201440_OID
      REMOVE BROM_1271
      REMOVE TYPE_1144
      REMOVE NAVNS_8396
      REMOVE BYGGE_8399
      REMOVE TENNS_8404
      REMOVE MAST_3700
      REMOVE LOST_3697
      REMOVE STFB_3755
      REMOVE STVE_3760
      REMOVE EIER_5810
      REMOVE EIERN_8397
      REMOVE VHAN_1554
      REMOVE JEVNK_8743
      REMOVE LUMKR_8740
      REMOVE AVIN_1714
      REMOVE TILSK_8398
      REMOVE UTEDR_8400
      REMOVE VDB_I_7656
      REMOVE SIDE
      REMOVE TOPOLOGY_LEVEL
      REMOVE DIMMI_10001
      REMOVE SHAPE_LEN
      REMOVE BA_200235_OID
      REMOVE BA_200280_OID
      REMOVE BA_200569_OID
      REMOVE BA_201418_OID
      REMOVE BA_201692_OID
      REMOVE VHAN_5638
      REMOVE EIER_7994
      REMOVE BEL_5637
      REMOVE VDB_I_7633
      REMOVE VAKA_1830
      REMOVE BA_202020_OID
      REMOVE BYGGE_10295
      REMOVE BREDG_2241
      REMOVE BREDH_10717
      REMOVE PUNKT_10718
      REMOVE BA_202126_OID
      REMOVE _COUNT
      REMOVE _TIMESTAMP
      REMOVE _WHERE
      REMOVE FME_FEATURE_TYPE_NAME
      REMOVE ATTRIBUTE{}.NAME
      REMOVE ATTRIBUTE{}.FME_DATA_TYPE
      REMOVE ATTRIBUTE{}.NATIVE_DATA_TYPE
      REMOVE FME_FORMAT_SHORT_NAME
      REMOVE FME_FORMAT_LONG_NAME
      REMOVE BA_200801_OID
      REMOVE MRK_5476
      REMOVE SKNR_5475
      RENAME_SET_VALUE DIRECTION > IKFB_DIRECTION
      REMOVE LANECODE
      REMOVE HT_200699_OID
      REMOVE BA_201568_OID
      REMOVE GTKD_4588
      REMOVE GTNV_4589
      REMOVE SIDEV_9793
      REMOVE BA_200670_OID
      REMOVE BA_201812_OID
      REMOVE TADT_4623
      REMOVE LANGX_4624
      REMOVE AR_4621
      REMOVE OPFR_6843
      REMOVE GRLG_4625
      REMOVE ANID_4620
      REMOVE TRAFA_7477
      REMOVE TPPM_5219
      REMOVE TPSD_5222
      REMOVE FADT_5220
      REMOVE FLNG_5221
      REMOVE KPAR_5223
      REMOVE MFAK_4622
      REMOVE AADTS_7475
      REMOVE AADTS_7476
      REMOVE VDB_I_7804
      REMOVE FYNR_4591
      REMOVE KMNR_4592
      REMOVE VKTG_4566
      REMOVE VSOV_4570
      REMOVE VGNR_4568
      REMOVE HP_4569
      REMOVE VSTS_4567
      REMOVE FRMT_4571
      REMOVE TLMT_4572
      REMOVE BRK1_4576
      REMOVE BRK2_4577
      REMOVE VGTP_4574
      REMOVE FVKD_4573
      REMOVE ENRG_4707
      REMOVE SVTP_4575
      REMOVE MDAT_4578
      REMOVE FLTO_5528
      REMOVE BA_200272_OID
      REMOVE BA_200952_OID
      REMOVE BA_201829_OID
      REMOVE FAGR_2021
      REMOVE VTNR_1891
      REMOVE VTDT_5124
      REMOVE JOURN_9155
      REMOVE VRFG_5125
      REMOVE GFDT_5127
      REMOVE TIDB_2071
      REMOVE VDB_I_7671
      REMOVE fme_feature_type
    -> EO_IKFB [Event_table_B]
EO_IKFB: EventOverlayer
    RoadLinkID = @Value(ROUTE_ID)
    FromVal = @Value(FROM_MEASURE)
    ToVal = @Value(TO_MEASURE)
    Common_Segments -> AttributeManager_7
    Only_A -> AttributeManager_7
    Only_B -> AttributeManager_7
AttributeManager_7
    ATTR_TABLE:
      SET_TO ROUTE_ID = @Value(RoadLinkID)
      SET_TO FROM_MEASURE = @Value(FromVal)
      SET_TO TO_MEASURE = @Value(ToVal)
      REMOVE RoadLinkID
      REMOVE FromVal
      REMOVE ToVal
      REMOVE _SegId
    -> EO_Trafikkmengde [Event_table_A]
Trafikkmengde (input)
    -> AttributeManager_8
AttributeManager_8
    ATTR_TABLE:
      REMOVE OBJECTID
      REMOVE NETOBJECTTV_ID
      REMOVE FROM_DATE
      REMOVE TO_DATE
      REMOVE SEQ_NO
      REMOVE BA_200026_OID
      REMOVE BA_200246_OID
      REMOVE BA_200558_OID
      REMOVE BA_201440_OID
      REMOVE BROM_1271
      REMOVE TYPE_1144
      REMOVE NAVNS_8396
      REMOVE BYGGE_8399
      REMOVE TENNS_8404
      REMOVE MAST_3700
      REMOVE LOST_3697
      REMOVE STFB_3755
      REMOVE STVE_3760
      REMOVE EIER_5810
      REMOVE EIERN_8397
      REMOVE VHAN_1554
      REMOVE JEVNK_8743
      REMOVE LUMKR_8740
      REMOVE AVIN_1714
      REMOVE TILSK_8398
      REMOVE UTEDR_8400
      REMOVE VDB_I_7656
      REMOVE SIDE
      REMOVE TOPOLOGY_LEVEL
      REMOVE DIMMI_10001
      REMOVE SHAPE_LEN
      REMOVE BA_200235_OID
      REMOVE BA_200280_OID
      REMOVE BA_200569_OID
      REMOVE BA_201418_OID
      REMOVE BA_201692_OID
      REMOVE VHAN_5638
      REMOVE EIER_7994
      REMOVE BEL_5637
      REMOVE VDB_I_7633
      REMOVE VAKA_1830
      REMOVE BA_202020_OID
      REMOVE BYGGE_10295
      REMOVE BREDG_2241
      REMOVE BREDH_10717
      REMOVE PUNKT_10718
      REMOVE BA_202126_OID
      REMOVE _COUNT
      REMOVE _TIMESTAMP
      REMOVE _WHERE
      REMOVE FME_FEATURE_TYPE_NAME
      REMOVE ATTRIBUTE{}.NAME
      REMOVE ATTRIBUTE{}.FME_DATA_TYPE
      REMOVE ATTRIBUTE{}.NATIVE_DATA_TYPE
      REMOVE FME_FORMAT_SHORT_NAME
      REMOVE FME_FORMAT_LONG_NAME
      REMOVE BA_200801_OID
      REMOVE MRK_5476
      REMOVE SKNR_5475
      REMOVE DIRECTION
      REMOVE LANECODE
      REMOVE HT_200699_OID
      REMOVE BA_201568_OID
      REMOVE GTKD_4588
      REMOVE GTNV_4589
      REMOVE SIDEV_9793
      REMOVE BA_200670_OID
      REMOVE BA_201812_OID
      RENAME_SET_VALUE TADT_4623 > aadt
      RENAME_SET_VALUE LANGX_4624 > andel_lange
      REMOVE AR_4621
      REMOVE OPFR_6843
      REMOVE GRLG_4625
      REMOVE ANID_4620
      REMOVE TRAFA_7477
      REMOVE TPPM_5219
      REMOVE TPSD_5222
      REMOVE FADT_5220
      REMOVE FLNG_5221
      REMOVE KPAR_5223
      REMOVE MFAK_4622
      REMOVE AADTS_7475
      REMOVE AADTS_7476
      REMOVE VDB_I_7804
      REMOVE FYNR_4591
      REMOVE KMNR_4592
      REMOVE VKTG_4566
      REMOVE VSOV_4570
      REMOVE VGNR_4568
      REMOVE HP_4569
      REMOVE VSTS_4567
      REMOVE FRMT_4571
      REMOVE TLMT_4572
      REMOVE BRK1_4576
      REMOVE BRK2_4577
      REMOVE VGTP_4574
      REMOVE FVKD_4573
      REMOVE ENRG_4707
      REMOVE SVTP_4575
      REMOVE MDAT_4578
      REMOVE FLTO_5528
      REMOVE BA_200272_OID
      REMOVE BA_200952_OID
      REMOVE BA_201829_OID
      REMOVE FAGR_2021
      REMOVE VTNR_1891
      REMOVE VTDT_5124
      REMOVE JOURN_9155
      REMOVE VRFG_5125
      REMOVE GFDT_5127
      REMOVE TIDB_2071
      REMOVE VDB_I_7671
      REMOVE fme_feature_type
    -> EO_Trafikkmengde [Event_table_B]
EO_Trafikkmengde: EventOverlayer
    RoadLinkID = @Value(ROUTE_ID)
    FromVal = @Value(FROM_MEASURE)
    ToVal = @Value(TO_MEASURE)
    Common_Segments -> AttributeManager_9
    Only_A -> AttributeManager_9
    Only_B -> AttributeManager_9
AttributeManager_9
    ATTR_TABLE:
      SET_TO ROUTE_ID = @Value(RoadLinkID)
      SET_TO FROM_MEASURE = @Value(FromVal)
      SET_TO TO_MEASURE = @Value(ToVal)
      REMOVE RoadLinkID
      REMOVE FromVal
      REMOVE ToVal
      REMOVE _SegId
    -> EO_Gate [Event_table_A]
Gate (input)
    -> AttributeManager_10
AttributeManager_10
    ATTR_TABLE:
      REMOVE OBJECTID
      REMOVE NETOBJECTTV_ID
      REMOVE FROM_DATE
      REMOVE TO_DATE
      REMOVE SEQ_NO
      REMOVE BA_200026_OID
      REMOVE BA_200246_OID
      REMOVE BA_200558_OID
      REMOVE BA_201440_OID
      REMOVE BROM_1271
      REMOVE TYPE_1144
      REMOVE NAVNS_8396
      REMOVE BYGGE_8399
      REMOVE TENNS_8404
      REMOVE MAST_3700
      REMOVE LOST_3697
      REMOVE STFB_3755
      REMOVE STVE_3760
      REMOVE EIER_5810
      REMOVE EIERN_8397
      REMOVE VHAN_1554
      REMOVE JEVNK_8743
      REMOVE LUMKR_8740
      REMOVE AVIN_1714
      REMOVE TILSK_8398
      REMOVE UTEDR_8400
      REMOVE VDB_I_7656
      REMOVE SIDE
      REMOVE TOPOLOGY_LEVEL
      REMOVE DIMMI_10001
      REMOVE SHAPE_LEN
      REMOVE BA_200235_OID
      REMOVE BA_200280_OID
      REMOVE BA_200569_OID
      REMOVE BA_201418_OID
      REMOVE BA_201692_OID
      REMOVE VHAN_5638
      REMOVE EIER_7994
      REMOVE BEL_5637
      REMOVE VDB_I_7633
      REMOVE VAKA_1830
      REMOVE BA_202020_OID
      REMOVE BYGGE_10295
      REMOVE BREDG_2241
      REMOVE BREDH_10717
      REMOVE PUNKT_10718
      REMOVE BA_202126_OID
      REMOVE _COUNT
      REMOVE _TIMESTAMP
      REMOVE _WHERE
      REMOVE FME_FEATURE_TYPE_NAME
      REMOVE ATTRIBUTE{}.NAME
      REMOVE ATTRIBUTE{}.FME_DATA_TYPE
      REMOVE ATTRIBUTE{}.NATIVE_DATA_TYPE
      REMOVE FME_FORMAT_SHORT_NAME
      REMOVE FME_FORMAT_LONG_NAME
      REMOVE BA_200801_OID
      REMOVE MRK_5476
      REMOVE SKNR_5475
      REMOVE DIRECTION
      REMOVE LANECODE
      REMOVE HT_200699_OID
      REMOVE BA_201568_OID
      REMOVE GTKD_4588
      REMOVE SIDEV_9793
      REMOVE BA_200670_OID
      REMOVE BA_201812_OID
      REMOVE TADT_4623
      REMOVE LANGX_4624
      REMOVE AR_4621
      REMOVE OPFR_6843
      REMOVE GRLG_4625
      REMOVE ANID_4620
      REMOVE TRAFA_7477
      REMOVE TPPM_5219
      REMOVE TPSD_5222
      REMOVE FADT_5220
      REMOVE FLNG_5221
      REMOVE KPAR_5223
      REMOVE MFAK_4622
      REMOVE AADTS_7475
      REMOVE AADTS_7476
      REMOVE VDB_I_7804
      REMOVE FYNR_4591
      REMOVE KMNR_4592
      REMOVE VKTG_4566
      REMOVE VSOV_4570
      REMOVE VGNR_4568
      REMOVE HP_4569
      REMOVE VSTS_4567
      REMOVE FRMT_4571
      REMOVE TLMT_4572
      REMOVE BRK1_4576
      REMOVE BRK2_4577
      REMOVE VGTP_4574
      REMOVE FVKD_4573
      REMOVE ENRG_4707
      REMOVE SVTP_4575
      REMOVE MDAT_4578
      REMOVE FLTO_5528
      REMOVE BA_200272_OID
      REMOVE BA_200952_OID
      REMOVE BA_201829_OID
      REMOVE FAGR_2021
      REMOVE VTNR_1891
      REMOVE VTDT_5124
      REMOVE JOURN_9155
      REMOVE VRFG_5125
      REMOVE GFDT_5127
      REMOVE TIDB_2071
      REMOVE VDB_I_7671
      REMOVE fme_feature_type
    -> EO_Gate [Event_table_B]
EO_Gate: EventOverlayer
    RoadLinkID = @Value(ROUTE_ID)
    FromVal = @Value(FROM_MEASURE)
    ToVal = @Value(TO_MEASURE)
    Common_Segments -> AttributeManager_11
    Only_A -> AttributeManager_11
    Only_B -> AttributeManager_11
AttributeManager_11
    ATTR_TABLE:
      SET_TO ROUTE_ID = @Value(RoadLinkID)
      SET_TO FROM_MEASURE = @Value(FromVal)
      SET_TO TO_MEASURE = @Value(ToVal)
      REMOVE RoadLinkID
      REMOVE FromVal
      REMOVE ToVal
      REMOVE _SegId
      REMOVE fartsgrense
    -> EO_Feltstrekning [Event_table_A]
Feltstrekning (input)
    -> AttributeManager_12
AttributeManager_12
    ATTR_TABLE:
      REMOVE OBJECTID
      REMOVE NETOBJECTTV_ID
      REMOVE FROM_DATE
      REMOVE TO_DATE
      REMOVE SEQ_NO
      REMOVE BA_200026_OID
      REMOVE BA_200246_OID
      REMOVE BA_200558_OID
      REMOVE BA_201440_OID
      REMOVE BROM_1271
      REMOVE TYPE_1144
      REMOVE NAVNS_8396
      REMOVE BYGGE_8399
      REMOVE TENNS_8404
      REMOVE MAST_3700
      REMOVE LOST_3697
      REMOVE STFB_3755
      REMOVE STVE_3760
      REMOVE EIER_5810
      REMOVE EIERN_8397
      REMOVE VHAN_1554
      REMOVE JEVNK_8743
      REMOVE LUMKR_8740
      REMOVE AVIN_1714
      REMOVE TILSK_8398
      REMOVE UTEDR_8400
      REMOVE VDB_I_7656
      REMOVE SIDE
      REMOVE TOPOLOGY_LEVEL
      REMOVE DIMMI_10001
      REMOVE SHAPE_LEN
      REMOVE BA_200235_OID
      REMOVE BA_200280_OID
      REMOVE BA_200569_OID
      REMOVE BA_201418_OID
      REMOVE BA_201692_OID
      REMOVE VHAN_5638
      REMOVE EIER_7994
      REMOVE BEL_5637
      REMOVE VDB_I_7633
      REMOVE VAKA_1830
      REMOVE BA_202020_OID
      REMOVE BYGGE_10295
      REMOVE BREDG_2241
      REMOVE BREDH_10717
      REMOVE PUNKT_10718
      REMOVE BA_202126_OID
      REMOVE _COUNT
      REMOVE _TIMESTAMP
      REMOVE _WHERE
      REMOVE FME_FEATURE_TYPE_NAME
      REMOVE ATTRIBUTE{}.NAME
      REMOVE ATTRIBUTE{}.FME_DATA_TYPE
      REMOVE ATTRIBUTE{}.NATIVE_DATA_TYPE
      REMOVE FME_FORMAT_SHORT_NAME
      REMOVE FME_FORMAT_LONG_NAME
      REMOVE BA_200801_OID
      REMOVE MRK_5476
      REMOVE SKNR_5475
      REMOVE DIRECTION
      REMOVE LANECODE
      REMOVE HT_200699_OID
      REMOVE BA_201568_OID
      REMOVE GTKD_4588
      REMOVE GTNV_4589
      REMOVE SIDEV_9793
      REMOVE BA_200670_OID
      REMOVE BA_201812_OID
      REMOVE TADT_4623
      REMOVE LANGX_4624
      REMOVE AR_4621
      REMOVE OPFR_6843
      REMOVE GRLG_4625
      REMOVE ANID_4620
      REMOVE TRAFA_7477
      REMOVE TPPM_5219
      REMOVE TPSD_5222
      REMOVE FADT_5220
      REMOVE FLNG_5221
      REMOVE KPAR_5223
      REMOVE MFAK_4622
      REMOVE AADTS_7475
      REMOVE AADTS_7476
      REMOVE VDB_I_7804
      REMOVE FYNR_4591
      REMOVE KMNR_4592
      REMOVE VKTG_4566
      REMOVE VSOV_4570
      REMOVE VGNR_4568
      REMOVE HP_4569
      REMOVE VSTS_4567
      REMOVE FRMT_4571
      REMOVE TLMT_4572
      REMOVE BRK1_4576
      REMOVE BRK2_4577
      REMOVE VGTP_4574
      REMOVE FVKD_4573
      REMOVE ENRG_4707
      REMOVE SVTP_4575
      REMOVE MDAT_4578
      REMOVE BA_200272_OID
      REMOVE BA_200952_OID
      REMOVE BA_201829_OID
      REMOVE FAGR_2021
      REMOVE VTNR_1891
      REMOVE VTDT_5124
      REMOVE JOURN_9155
      REMOVE VRFG_5125
      REMOVE GFDT_5127
      REMOVE TIDB_2071
      REMOVE VDB_I_7671
      REMOVE fme_feature_type
    -> EO_Feltstrekning [Event_table_B]
EO_Feltstrekning: EventOverlayer
    RoadLinkID = @Value(ROUTE_ID)
    FromVal = @Value(FROM_MEASURE)
    ToVal = @Value(TO_MEASURE)
    Common_Segments -> AttributeManager_13
    Only_A -> AttributeManager_13
    Only_B -> AttributeManager_13
AttributeManager_13
    ATTR_TABLE:
      SET_TO ROUTE_ID = @Value(RoadLinkID)
      SET_TO FROM_MEASURE = @Value(FromVal)
      SET_TO TO_MEASURE = @Value(ToVal)
      REMOVE RoadLinkID
      REMOVE FromVal
      REMOVE ToVal
      REMOVE _SegId
      REMOVE fartsgrense
    -> EO_Fartsgrense [Event_table_A]
Fartsgrense (input)
    -> AttributeValueMapper_2
AttributeValueMapper_2
    SRC = FAGR_2021
    VAL_ATTR = fartsgrense
    LUT = 11576,20,2726,30,2728,40,2730,50,2732,60,2735,70,2738,80,2741,90,5087,100
    DIRECTION = Forward (Source To Destination)
    DEFAULT_VALUE = 80
    -> AttributeManager_15
AttributeManager_15
    ATTR_TABLE:
      REMOVE OBJECTID
      REMOVE NETOBJECTTV_ID
      REMOVE FROM_DATE
      REMOVE TO_DATE
      REMOVE SEQ_NO
      REMOVE BA_200026_OID
      REMOVE BA_200246_OID
      REMOVE BA_200558_OID
      REMOVE BA_201440_OID
      REMOVE BROM_1271
      REMOVE TYPE_1144
      REMOVE NAVNS_8396
      REMOVE BYGGE_8399
      REMOVE TENNS_8404
      REMOVE MAST_3700
      REMOVE LOST_3697
      REMOVE STFB_3755
      REMOVE STVE_3760
      REMOVE EIER_5810
      REMOVE EIERN_8397
      REMOVE VHAN_1554
      REMOVE JEVNK_8743
      REMOVE LUMKR_8740
      REMOVE AVIN_1714
      REMOVE TILSK_8398
      REMOVE UTEDR_8400
      REMOVE VDB_I_7656
      REMOVE SIDE
      REMOVE TOPOLOGY_LEVEL
      REMOVE DIMMI_10001
      REMOVE SHAPE_LEN
      REMOVE BA_200235_OID
      REMOVE BA_200280_OID
      REMOVE BA_200569_OID
      REMOVE BA_201418_OID
      REMOVE BA_201692_OID
      REMOVE VHAN_5638
      REMOVE EIER_7994
      REMOVE BEL_5637
      REMOVE VDB_I_7633
      REMOVE VAKA_1830
      REMOVE BA_202020_OID
      REMOVE BYGGE_10295
      REMOVE BREDG_2241
      REMOVE BREDH_10717
      REMOVE PUNKT_10718
      REMOVE BA_202126_OID
      REMOVE _COUNT
      REMOVE _TIMESTAMP
      REMOVE _WHERE
      REMOVE FME_FEATURE_TYPE_NAME
      REMOVE ATTRIBUTE{}.NAME
      REMOVE ATTRIBUTE{}.FME_DATA_TYPE
      REMOVE ATTRIBUTE{}.NATIVE_DATA_TYPE
      REMOVE FME_FORMAT_SHORT_NAME
      REMOVE FME_FORMAT_LONG_NAME
      REMOVE BA_200801_OID
      REMOVE MRK_5476
      REMOVE SKNR_5475
      REMOVE DIRECTION
      REMOVE LANECODE
      REMOVE HT_200699_OID
      REMOVE BA_201568_OID
      REMOVE GTKD_4588
      REMOVE GTNV_4589
      REMOVE SIDEV_9793
      REMOVE BA_200670_OID
      REMOVE BA_201812_OID
      REMOVE TADT_4623
      REMOVE LANGX_4624
      REMOVE AR_4621
      REMOVE OPFR_6843
      REMOVE GRLG_4625
      REMOVE ANID_4620
      REMOVE TRAFA_7477
      REMOVE TPPM_5219
      REMOVE TPSD_5222
      REMOVE FADT_5220
      REMOVE FLNG_5221
      REMOVE KPAR_5223
      REMOVE MFAK_4622
      REMOVE AADTS_7475
      REMOVE AADTS_7476
      REMOVE VDB_I_7804
      REMOVE FYNR_4591
      REMOVE KMNR_4592
      REMOVE VKTG_4566
      REMOVE VSOV_4570
      REMOVE VGNR_4568
      REMOVE HP_4569
      REMOVE VSTS_4567
      REMOVE FRMT_4571
      REMOVE TLMT_4572
      REMOVE BRK1_4576
      REMOVE BRK2_4577
      REMOVE VGTP_4574
      REMOVE FVKD_4573
      REMOVE ENRG_4707
      REMOVE SVTP_4575
      REMOVE MDAT_4578
      REMOVE FLTO_5528
      REMOVE BA_200272_OID
      REMOVE BA_200952_OID
      REMOVE BA_201829_OID
      REMOVE FAGR_2021
      REMOVE VTNR_1891
      REMOVE VTDT_5124
      REMOVE JOURN_9155
      REMOVE VRFG_5125
      REMOVE GFDT_5127
      REMOVE TIDB_2071
      REMOVE VDB_I_7671
      REMOVE fme_feature_type
    -> EO_Fartsgrense [Event_table_B]
EO_Fartsgrense: EventOverlayer
    RoadLinkID = @Value(ROUTE_ID)
    FromVal = @Value(FROM_MEASURE)
    ToVal = @Value(TO_MEASURE)
    Common_Segments -> AttributeManager_14
    Only_A -> AttributeManager_14
    Only_B -> AttributeManager_14
AttributeManager_14
    ATTR_TABLE:
      SET_TO ROUTE_ID = @Value(RoadLinkID)
      SET_TO FROM_MEASURE = @Value(FromVal)
      SET_TO TO_MEASURE = @Value(ToVal)
      REMOVE RoadLinkID
      REMOVE FromVal
      REMOVE ToVal
      REMOVE _SegId
    -> EO_Vegreferanse [Event_table_A]
Vegreferanse (input)
    -> TestFilter_2
TestFilter_2
    TEST_LIST:
      BOOL_OP,AND,COMPOSITE_TEST,<Unused>,TEST_CLAUSE,"TEST ""@Value(FVKD_4573)"" != ""5512""
      TEST ""@Value(VSTS_4567)"" IN ""5499,5502,5503,5504,5505,12159,12983""",VEGREFERANSE
    DEFAULT_VALUE = <UNFILTERED>
    VEGREFERANSE -> AttributeManager_16
AttributeManager_16
    ATTR_TABLE:
      REMOVE OBJECTID
      REMOVE NETOBJECTTV_ID
      REMOVE FROM_DATE
      REMOVE TO_DATE
      REMOVE SEQ_NO
      REMOVE BA_200026_OID
      REMOVE BA_200246_OID
      REMOVE BA_200558_OID
      REMOVE BA_201440_OID
      REMOVE BROM_1271
      REMOVE TYPE_1144
      REMOVE NAVNS_8396
      REMOVE BYGGE_8399
      REMOVE TENNS_8404
      REMOVE MAST_3700
      REMOVE LOST_3697
      REMOVE STFB_3755
      REMOVE STVE_3760
      REMOVE EIER_5810
      REMOVE EIERN_8397
      REMOVE VHAN_1554
      REMOVE JEVNK_8743
      REMOVE LUMKR_8740
      REMOVE AVIN_1714
      REMOVE TILSK_8398
      REMOVE UTEDR_8400
      REMOVE VDB_I_7656
      REMOVE SIDE
      REMOVE TOPOLOGY_LEVEL
      REMOVE DIMMI_10001
      REMOVE SHAPE_LEN
      REMOVE BA_200235_OID
      REMOVE BA_200280_OID
      REMOVE BA_200569_OID
      REMOVE BA_201418_OID
      REMOVE BA_201692_OID
      REMOVE VHAN_5638
      REMOVE EIER_7994
      REMOVE BEL_5637
      REMOVE VDB_I_7633
      REMOVE VAKA_1830
      REMOVE BA_202020_OID
      REMOVE BYGGE_10295
      REMOVE BREDG_2241
      REMOVE BREDH_10717
      REMOVE PUNKT_10718
      REMOVE BA_202126_OID
      REMOVE _COUNT
      REMOVE _TIMESTAMP
      REMOVE _WHERE
      REMOVE FME_FEATURE_TYPE_NAME
      REMOVE ATTRIBUTE{}.NAME
      REMOVE ATTRIBUTE{}.FME_DATA_TYPE
      REMOVE ATTRIBUTE{}.NATIVE_DATA_TYPE
      REMOVE FME_FORMAT_SHORT_NAME
      REMOVE FME_FORMAT_LONG_NAME
      REMOVE BA_200801_OID
      REMOVE MRK_5476
      REMOVE SKNR_5475
      REMOVE DIRECTION
      REMOVE LANECODE
      REMOVE HT_200699_OID
      REMOVE BA_201568_OID
      REMOVE GTKD_4588
      REMOVE GTNV_4589
      REMOVE SIDEV_9793
      REMOVE BA_200670_OID
      REMOVE BA_201812_OID
      REMOVE TADT_4623
      REMOVE LANGX_4624
      REMOVE AR_4621
      REMOVE OPFR_6843
      REMOVE GRLG_4625
      REMOVE ANID_4620
      REMOVE TRAFA_7477
      REMOVE TPPM_5219
      REMOVE TPSD_5222
      REMOVE FADT_5220
      REMOVE FLNG_5221
      REMOVE KPAR_5223
      REMOVE MFAK_4622
      REMOVE AADTS_7475
      REMOVE AADTS_7476
      REMOVE VDB_I_7804
      REMOVE FYNR_4591
      REMOVE KMNR_4592
      REMOVE VSOV_4570
      REMOVE FRMT_4571
      REMOVE TLMT_4572
      REMOVE BRK1_4576
      REMOVE BRK2_4577
      REMOVE VGTP_4574
      REMOVE FVKD_4573
      REMOVE ENRG_4707
      REMOVE SVTP_4575
      REMOVE MDAT_4578
      REMOVE FLTO_5528
      REMOVE BA_200272_OID
      REMOVE BA_200952_OID
      REMOVE BA_201829_OID
      REMOVE FAGR_2021
      REMOVE VTNR_1891
      REMOVE VTDT_5124
      REMOVE JOURN_9155
      REMOVE VRFG_5125
      REMOVE GFDT_5127
      REMOVE TIDB_2071
      REMOVE VDB_I_7671
      REMOVE fme_feature_type
    -> EO_Vegreferanse [Event_table_B]
EO_Vegreferanse: EventOverlayer
    RoadLinkID = @Value(ROUTE_ID)
    FromVal = @Value(FROM_MEASURE)
    ToVal = @Value(TO_MEASURE)
    Common_Segments -> AttributeManager_17
    Only_B -> AttributeManager_17
AttributeManager_17
    ATTR_TABLE:
      SET_TO ROUTE_ID = @Value(RoadLinkID)
      SET_TO FROM_MEASURE = @Value(FromVal)
      SET_TO TO_MEASURE = @Value(ToVal)
      REMOVE RoadLinkID
      REMOVE FromVal
      REMOVE ToVal
      REMOVE _SegId
    -> Segmenter (output)
Segmenter (output)

FME custom transformer NULL
Does nothing

Input (input)
    -> Output (output)
Output (output)

FME custom transformer SegmentizeTable
Splits an event table based on a list of segments with from-to-measure

Parameters:
- eventRoadLink =   # Event Table Road Link ID Attribute
- eventFromVal =   # Event Table from meassure
- eventToVal =   # Event Table To Meassure

Events (input)
    -> AttributeCreator
SegmentList (input)
    -> AttributeExposer
Note: Create common segments
InlineQuerier
    QUERY_DEF:
      EventSegments,Select * FROM Events
      INNER JOIN Segments ON Events.RoadLinkID = Segments.RoadLinkID
      WHERE (Segments.segFromVal < Events.eventToVal AND Segments.segToVal > Events.eventFromVal),FIRST
    QUERY_SCHEMA = EventSegments,RoadLinkID,varchar(30),eventFromVal,float,eventToVal,float,Events.fme_feature_content,fme_feature_content,segFromVal,float,segToVal,float,Segments.fme_feature_content,fme_feature_content
    TABLE_DEF = Events,RoadLinkID,varchar(30),eventFromVal,float,eventToVal,float,Segments,RoadLinkID,varchar(30),segFromVal,float,segToVal,float
    EventSegments -> AttributeManager
AttributeManager
    ATTR_TABLE:
      SET_TO FromVal = @Value(segFromVal)
      SET_TO ToVal = @Value(segToVal)
      REMOVE eventFromVal
      REMOVE eventToVal
      REMOVE segFromVal
      REMOVE segToVal
    -> Segmented (output)
Segmented (output)

Bookmark: Link ID and measure attributes
AttributeCreator
    ATTR_TABLE:
      SET_TO RoadLinkID = $(eventRoadLink)
      SET_TO eventFromVal = $(eventFromVal)
      SET_TO eventToVal = $(eventToVal)
    -> InlineQuerier [Events]
AttributeExposer
    ATTR_LIST = RoadLinkID,FromVal,ToVal
    -> AttributeExpressionRenamer
AttributeExpressionRenamer: BulkAttributeRenamer
    REPLACE_STR = seg
    ATTRCHOICE = Selected Attributes
    MODE_CHOICE = RENAME
    PATTERN_ACTION_DISP = ADDPREFIX
    ATTRLIST = FromVal ToVal
    -> InlineQuerier [Segments]
